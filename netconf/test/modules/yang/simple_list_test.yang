module simple_list_test {

    namespace "http://netconfcentral.org/ns/simple_list_test";
    prefix "slt";

    revision 2008-11-20 {
        description "Initial revision.";
    }

    container simple_list {
      list theList {
        key theKey;
        leaf theKey { type string; }
        leaf theVal { type string; }
      }
    }

    rpc inc-counter {
        description "Increments a counter.";
    }

    rpc get-counter {
        description "Gets the current count.";

        output {
            leaf count {
                description "The current count.";
                type uint32;
            }
        }
    }
}
