/*
 * This module has been generated by smidump 0.4.6:
 *
 *      smidump -f yang --yang-smi-extensions RFC-1215
 *
 * Do not edit. Edit the source file instead!
 */

module RFC-1215 {

   /*** NAMESPACE / PREFIX DEFINITION ***/

   namespace "urn:ietf:params:xml:ns:yang:smiv2:RFC-1215";
   prefix "rfc-1215";

   /*** LINKAGE (IMPORTS / INCLUDES) ***/

   import yang-smi { prefix "smi"; }

   /*** META INFORMATION ***/

   organization     
     "";

   contact          
     "";

   description      
     "";

   revision "1991-03-01" {
     description 
       "From RFC 1215.";
   }

} /* end of module RFC-1215 */
