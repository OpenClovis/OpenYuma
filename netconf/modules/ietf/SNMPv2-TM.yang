/*
 * This module has been generated by smidump 0.4.6:
 *
 *      smidump -f yang --yang-smi-extensions SNMPv2-TM
 *
 * Do not edit. Edit the source file instead!
 */

module SNMPv2-TM {

   /*** NAMESPACE / PREFIX DEFINITION ***/

   namespace "urn:ietf:params:xml:ns:yang:smiv2:SNMPv2-TM";
   prefix "snmpv2-tm";

   /*** LINKAGE (IMPORTS / INCLUDES) ***/

   import yang-smi { prefix "smi"; }

   /*** META INFORMATION ***/

   organization     
     "IETF SNMPv3 Working Group";

   contact          
     "WG-EMail:   snmpv3@lists.tislabs.com
      Subscribe:  snmpv3-request@lists.tislabs.com
      
      Co-Chair:   Russ Mundy
                  Network Associates Laboratories
      postal:     15204 Omega Drive, Suite 300
                  Rockville, MD 20850-4601
                  USA
      EMail:      mundy@tislabs.com
      phone:      +1 301 947-7107
      
      Co-Chair:   David Harrington
                  Enterasys Networks
      postal:     35 Industrial Way
                  P. O. Box 5005
                  Rochester, NH 03866-5005
                  USA
      EMail:      dbh@enterasys.com
      phone:      +1 603 337-2614
      
      Editor:     Randy Presuhn
                  BMC Software, Inc.
      postal:     2141 North First Street
                  San Jose, CA 95131
                  USA
      EMail:      randy_presuhn@bmc.com
      phone:      +1 408 546-1006";

   description      
     "The MIB module for SNMP transport mappings.
      
      Copyright (C) The Internet Society (2002). This
      version of this MIB module is part of RFC 3417;
      see the RFC itself for full legal notices.";

   revision "2002-10-16" {
      description   
        "Clarifications, published as RFC 3417.";
   }
   revision "1996-01-01" {
      description   
        "Clarifications, published as RFC 1906.";
   }
   revision "1993-04-01" {
      description   
        "The initial version, published as RFC 1449.";
   }

   /*** TYPE DEFINITIONS ***/

   typedef SnmpUDPAddress {
      type string {
         length "6";
         pattern "((0|[1-9](([0-9]){0,2}))(0|[1-9](([0-9]){0,2}))(0|[1-9](([0-9]){0,2}))(0|[1-9](([0-9]){0,2}))((0|[1-9](([0-9]){0,4})){1,1})(0|[1-9](([0-9]){0,4})))";
      }
      description   
        "Represents a UDP over IPv4 address:
         
         octets   contents        encoding
          1-4     IP-address      network-byte order
          5-6     UDP-port        network-byte order";
      smi:display-hint "1d.1d.1d.1d/2d";
   }

   typedef SnmpOSIAddress {
      type string {
         length "1 | 4..85";
      }
      description   
        "Represents an OSI transport-address:
         
         octets   contents           encoding
            1     length of NSAP     'n' as an unsigned-integer
                                        (either 0 or from 3 to 20)
         2..(n+1) NSAP                concrete binary representation
         (n+2)..m TSEL                string of (up to 64) octets
           ";
      smi:display-hint "*1x:/1x:";
   }

   typedef SnmpNBPAddress {
      type binary {
         length "3..99";
      }
      description   
        "Represents an NBP name:
         
         octets        contents          encoding
            1          length of object  'n' as an unsigned integer
          2..(n+1)     object            string of (up to 32) octets
           n+2         length of type    'p' as an unsigned integer
         (n+3)..(n+2+p)   type              string of (up to 32) octets
          n+3+p        length of zone    'q' as an unsigned integer
         (n+4+p)..(n+3+p+q) zone              string of (up to 32) octets
         
            For comparison purposes, strings are
            case-insensitive. All strings may contain any octet
            other than 255 (hex ff).";
   }

   typedef SnmpIPXAddress {
      type string {
         length "12";
         pattern "((([0-9A-Fa-f]{2}){4})(([0-9A-Fa-f]{2}){1})(([0-9A-Fa-f]{2}){1})(([0-9A-Fa-f]{2}){1})(([0-9A-Fa-f]{2}){1})(([0-9A-Fa-f]{2}){1})(([0-9A-Fa-f]{2}){1})((0|[1-9](([0-9]){0,4})){1,1})(0|[1-9](([0-9]){0,4})))";
      }
      description   
        "Represents an IPX address:
         
         octets   contents            encoding
          1-4     network-number      network-byte order
          5-10    physical-address    network-byte order
         11-12    socket-number       network-byte order";
      smi:display-hint "4x.1x:1x:1x:1x:1x:1x.2d";
   }

} /* end of module SNMPv2-TM */
