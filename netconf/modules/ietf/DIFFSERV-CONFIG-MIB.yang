/*
 * This module has been generated by smidump 0.4.6:
 *
 *      smidump -f yang --yang-smi-extensions DIFFSERV-CONFIG-MIB
 *
 * Do not edit. Edit the source file instead!
 */

module DIFFSERV-CONFIG-MIB {

   /*** NAMESPACE / PREFIX DEFINITION ***/

   namespace "urn:ietf:params:xml:ns:yang:smiv2:DIFFSERV-CONFIG-MIB";
   prefix "diffserv-config";

   /*** LINKAGE (IMPORTS / INCLUDES) ***/

   import SNMP-FRAMEWORK-MIB { prefix "snmp-framework"; }
   import SNMPv2-TC          { prefix "smiv2"; }
   import yang-smi           { prefix "smi"; }

   /*** META INFORMATION ***/

   organization     
     "SNMPCONF WG";

   contact          
     "SNMPCONF Working Group
      http://www.ietf.org/html.charters/snmpconf-charter.html
      WG mailing list: snmpconf@snmp.com
      
      Editors:
      Harrie Hazewinkel
      I.Net
      via Darwin 85
      20019 - Settimo Milanese (MI)
      Italy
      EMail: harrie@inet.it
      
      David Partain
      Ericsson AB
      P.O. Box 1248
      SE-581 12 Linkoping
      Sweden
      E-mail: David.Partain@ericsson.com";

   description      
     "This MIB module contains differentiated services
      specific managed objects to perform higher-level
      configuration management.  This MIB allows policies
      to use 'templates' to instantiate Differentiated
      Services functional datapath configurations to
      be assigned (associated with an interface and
      direction) when a policy is activated.
      
      Copyright (C) The Internet Society (2004).  This version
      of this MIB module is part of RFC 3747;  see the RFC
      itself for full legal notices.";

   revision "2004-01-22" {
      description   
        "Initial version published as RFC 3747";
   }

   container diffServConfigMIBObjects {


      /* XXX table comments here XXX */

      list diffServConfigEntry {

         key "diffServConfigId";
         description 
           "An entry defining a per-hop-behavior.  Each entry in
            this table combines the various parameters (entries)
            into a specific per-hop-behavior.  Entries in this
            table might be defined by a vendor (pre-configured)
            or defined by a management application.";
         smi:oid "1.3.6.1.2.1.108.1.2.1";


         leaf diffServConfigId {
            type snmp-framework:SnmpAdminString {
               length "1..116";
            }
            // config false;
            description   
              "A unique id for the per-hop-behavior policy for at
               least the SNMP agent.  For ease of administration the
               value may be unique within an administrative domain,
               but this is not required.
               
               The range of up to 116 octets is chosen to stay within
               the SMI limit of 128 sub-identifiers in an object
               identifier.";
            smi:oid "1.3.6.1.2.1.108.1.2.1.1";
         }

         leaf diffServConfigDescr {
            type snmp-framework:SnmpAdminString;
            config true;
            description   
              "A human-readable description to identify this defined
               per-hop-behavior.  Note that this is an SnmpAdminString,
               which permits UTF-8 strings.  An administratively assigned
               identifier for a template that would be unique within
               an administrative domain.  It is up to the management
               applications to agree how these are assigned within the
               administrative domain.  Once a description, such as
               'EF' is assigned, that has a certain set of parameters
               that achieve 'EF' from box to box. Management
               application code or script code can then scan
               the table to find the proper template and then
               assign it.";
            smi:oid "1.3.6.1.2.1.108.1.2.1.2";
         }

         leaf diffServConfigOwner {
            type snmp-framework:SnmpAdminString;
            config true;
            description   
              "The owner who created this entry.";
            smi:oid "1.3.6.1.2.1.108.1.2.1.3";
         }

         leaf diffServConfigLastChange {
            type smiv2:DateAndTime;
            config false;
            description   
              "The date and time when this entry was last changed.";
            smi:oid "1.3.6.1.2.1.108.1.2.1.4";
         }

         leaf diffServConfigStart {
            type smiv2:RowPointer;
            config true;
            description   
              "The pointer to a functional datapath configuration template as
               set up in the DIFFSERV-MIB.  This RowPointer should
               point to an instance of one of:
                 diffServClfrEntry
                 diffServMeterEntry
                 diffServActionEntry
                 diffServAlgDropEntry
                 diffServQEntry
               
               
               
               
               A value of zeroDotZero in this attribute indicates no
               further Diffserv treatment is performed on traffic of
               this functional datapath.  This also means that the
               template described by this row is not defined.
               
               If the row pointed to does not exist, the treatment
               is as if this attribute contains a value of zeroDotZero.";
            reference 
              "Differentiated Services MIB module";
            smi:default "zeroDotZero";
            smi:oid "1.3.6.1.2.1.108.1.2.1.5";
         }

         leaf diffServConfigStorage {
            type smiv2:StorageType;
            config true;
            description   
              "The type of storage used for this row.
               
               Since an entry in this table serves as a starting
               point for a configuration, it is recommended that
               all entries comprising the configuration started by
               diffServConfigStart follow the storage type of this
               entry.  Otherwise, after agent reboots a configuration
               may differ.  It may very well be that the agent is
               not capable of detecting such changes and therefore,
               the management application should verify the correct
               configuration after a reboot.  Rows with a StorageType
               of 'permanent' do not need to allow write access to
               any of the columnar objects in that row.";
            smi:default "nonVolatile";
            smi:oid "1.3.6.1.2.1.108.1.2.1.6";
         }

         leaf diffServConfigStatus {
            type smiv2:RowStatus;
            config true;
            description   
              "RowStatus object used for creation and deletion of
               rows in this table.  All writable objects in this row
               may be modified at any time.";
            smi:default "notInService";
            smi:oid "1.3.6.1.2.1.108.1.2.1.7";
         }
      }
      smi:oid "1.3.6.1.2.1.108.1";
   }

} /* end of module DIFFSERV-CONFIG-MIB */
