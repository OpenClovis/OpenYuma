/*
 * This module has been generated by smidump 0.4.6:
 *
 *      smidump -f yang --yang-smi-extensions DISMAN-EVENT-MIB
 *
 * Do not edit. Edit the source file instead!
 */

module DISMAN-EVENT-MIB {

   /*** NAMESPACE / PREFIX DEFINITION ***/

   namespace "urn:ietf:params:xml:ns:yang:smiv2:DISMAN-EVENT-MIB";
   prefix "disman-event";

   /*** LINKAGE (IMPORTS / INCLUDES) ***/

   import SNMP-FRAMEWORK-MIB { prefix "snmp-framework"; }
   import SNMP-TARGET-MIB    { prefix "snmp-target"; }
   import SNMPv2-MIB         { prefix "snmpv2-mib"; }
   import SNMPv2-TC          { prefix "smiv2"; }
   import yang-smi           { prefix "smi"; }
   import ietf-yang-types    { prefix "yang"; }

   /*** META INFORMATION ***/

   organization     
     "IETF Distributed Management Working Group";

   contact          
     "Ramanathan Kavasseri
      Cisco Systems, Inc.
      170 West Tasman Drive,
      San Jose CA 95134-1706.
      Phone: +1 408 526 4527
      Email: ramk@cisco.com";

   description      
     "The MIB module for defining event triggers and actions
      for network management purposes.";

   revision "2000-10-16" {
      description   
        "This is the initial version of this MIB.
         Published as RFC 2981";
   }

   /*** TYPE DEFINITIONS ***/

   typedef FailureReason {
      type enumeration {
         enum sampleOverrun          { value -6; }
         enum badType                { value -5; }
         enum noResponse             { value -4; }
         enum destinationUnreachable { value -3; }
         enum badDestination         { value -2; }
         enum localResourceLack      { value -1; }
         enum noError                { value 0; }
         enum tooBig                 { value 1; }
         enum noSuchName             { value 2; }
         enum badValue               { value 3; }
         enum readOnly               { value 4; }
         enum genErr                 { value 5; }
         enum noAccess               { value 6; }
         enum wrongType              { value 7; }
         enum wrongLength            { value 8; }
         enum wrongEncoding          { value 9; }
         enum wrongValue             { value 10; }
         enum noCreation             { value 11; }
         enum inconsistentValue      { value 12; }
         enum resourceUnavailable    { value 13; }
         enum commitFailed           { value 14; }
         enum undoFailed             { value 15; }
         enum authorizationError     { value 16; }
         enum notWritable            { value 17; }
         enum inconsistentName       { value 18; }
      }
      description   
        "Reasons for failures in an attempt to perform a management
         request.
         
         The first group of errors, numbered less than 0, are related
         to problems in sending the request.  The existence of a
         particular error code here does not imply that all
         implementations are capable of sensing that error and
         
         
         returning that code.
         
         The second group, numbered greater than 0, are copied
         directly from SNMP protocol operations and are intended to
         carry exactly the meanings defined for the protocol as returned
         in an SNMP response.
         
         localResourceLack       some local resource such as memory
                                 lacking or
                                 mteResourceSampleInstanceMaximum
                                 exceeded
         badDestination          unrecognized domain name or otherwise
                                 invalid destination address
         destinationUnreachable  can't get to destination address
         noResponse              no response to SNMP request
         badType                 the data syntax of a retrieved object
                                 as not as expected
         sampleOverrun           another sample attempt occurred before
                                 the previous one completed";
   }

   container mteResource {

      leaf mteResourceSampleMinimum {
         type int32 {
            range "1..2147483647";
         }
         units "seconds";
         config true;
         description 
           "The minimum mteTriggerFrequency this system will
            accept.  A system may use the larger values of this minimum to
            lessen the impact of constant sampling.  For larger
            sampling intervals the system samples less often and
            suffers less overhead.  This object provides a way to enforce
            such lower overhead for all triggers created after it is
            set.
            
            Unless explicitly resource limited, a system's value for
            this object SHOULD be 1, allowing as small as a 1 second
            interval for ongoing trigger sampling.
            
            Changing this value will not invalidate an existing setting
            of mteTriggerFrequency.";
         smi:oid "1.3.6.1.2.1.88.1.1.1";
      }

      leaf mteResourceSampleInstanceMaximum {
         type uint32;
         units "instances";
         config true;
         description 
           "The maximum number of instance entries this system will
            support for sampling.
            
            These are the entries that maintain state, one for each
            instance of each sampled object as selected by
            mteTriggerValueID.  Note that wildcarded objects result
            in multiple instances of this state.
            
            A value of 0 indicates no preset limit, that is, the limit
            is dynamic based on system operation and resources.
            
            Unless explicitly resource limited, a system's value for
            this object SHOULD be 0.
            
            Changing this value will not eliminate or inhibit existing
            sample state but could prevent allocation of additional state
            information.";
         smi:oid "1.3.6.1.2.1.88.1.1.2";
      }

      leaf mteResourceSampleInstances {
         type yang:gauge32;
         units "instances";
         config false;
         description 
           "The number of currently active instance entries as
            defined for mteResourceSampleInstanceMaximum.";
         smi:oid "1.3.6.1.2.1.88.1.1.3";
      }

      leaf mteResourceSampleInstancesHigh {
         type yang:gauge32;
         units "instances";
         config false;
         description 
           "The highest value of mteResourceSampleInstances that has
            occurred since initialization of the management system.";
         smi:oid "1.3.6.1.2.1.88.1.1.4";
      }

      leaf mteResourceSampleInstanceLacks {
         type yang:counter32;
         units "instances";
         config false;
         description 
           "The number of times this system could not take a new sample
            because that allocation would have exceeded the limit set by
            mteResourceSampleInstanceMaximum.";
         smi:oid "1.3.6.1.2.1.88.1.1.5";
      }
      smi:oid "1.3.6.1.2.1.88.1.1";
   }

   container mteTrigger {

      leaf mteTriggerFailures {
         type yang:counter32;
         units "failures";
         config false;
         description 
           "The number of times an attempt to check for a trigger
            condition has failed.  This counts individually for each
            attempt in a group of targets or each attempt for a
            
            
            wildcarded object.";
         smi:oid "1.3.6.1.2.1.88.1.2.1";
      }


      /* XXX table comments here XXX */

      list mteTriggerEntry {

         key "mteOwner mteTriggerName";
         description 
           "Information about a single trigger.  Applications create and
            delete entries using mteTriggerEntryStatus.";
         smi:oid "1.3.6.1.2.1.88.1.2.2.1";


         leaf mteOwner {
            type snmp-framework:SnmpAdminString {
               length "0..32";
            }
            // config false;
            description   
              "The owner of this entry. The exact semantics of this
               string are subject to the security policy defined by the
               security administrator.";
            smi:oid "1.3.6.1.2.1.88.1.2.2.1.1";
         }

         leaf mteTriggerName {
            type snmp-framework:SnmpAdminString {
               length "1..32";
            }
            // config false;
            description   
              "A locally-unique, administratively assigned name for the
               trigger within the scope of mteOwner.";
            smi:oid "1.3.6.1.2.1.88.1.2.2.1.2";
         }

         leaf mteTriggerComment {
            type snmp-framework:SnmpAdminString;
            config true;
            description   
              "A description of the trigger's function and use.";
            smi:default "";
            smi:oid "1.3.6.1.2.1.88.1.2.2.1.3";
         }

         leaf mteTriggerTest {
            type bits {
               bit existence { position 0; }
               bit boolean   { position 1; }
               bit threshold { position 2; }
            }
            config true;
            description   
              "The type of trigger test to perform.  For 'boolean' and
               'threshold'  tests, the object at mteTriggerValueID MUST
               evaluate to an integer, that is, anything that ends up encoded
               for transmission (that is, in BER, not ASN.1) as an integer.
               
               For 'existence', the specific test is as selected by
               mteTriggerExistenceTest.  When an object appears, vanishes
               or changes value, the trigger fires. If the object's
               appearance caused the trigger firing, the object MUST
               vanish before the trigger can be fired again for it, and
               vice versa. If the trigger fired due to a change in the
               object's value, it will be fired again on every successive
               value change for that object.
               
               For 'boolean', the specific test is as selected by
               mteTriggerBooleanTest.  If the test result is true the trigger
               fires.  The trigger will not fire again until the value has
               become false and come back to true.
               
               For 'threshold' the test works as described below for
               
               
               mteTriggerThresholdStartup, mteTriggerThresholdRising, and
               mteTriggerThresholdFalling.
               
               Note that combining 'boolean' and 'threshold' tests on the
               same object may be somewhat redundant.";
            smi:default "6)";
            smi:oid "1.3.6.1.2.1.88.1.2.2.1.4";
         }

         leaf mteTriggerSampleType {
            type enumeration {
               enum absoluteValue { value 1; }
               enum deltaValue    { value 2; }
            }
            config true;
            description   
              "The type of sampling to perform.
               
               An 'absoluteValue' sample requires only a single sample to be
               meaningful, and is exactly the value of the object at
               mteTriggerValueID at the sample time.
               
               A 'deltaValue' requires two samples to be meaningful and is
               thus not available for testing until the second and subsequent
               samples after the object at mteTriggerValueID is first found
               to exist.  It is the difference between the two samples.  For
               unsigned values it is always positive, based on unsigned
               arithmetic.  For signed values it can be positive or negative.
               
               For SNMP counters to be meaningful they should be sampled as a
               'deltaValue'.
               
               For 'deltaValue' mteTriggerDeltaTable contains further
               parameters.
               
               If only 'existence' is set in mteTriggerTest this object has
               no meaning.";
            smi:default "absoluteValue";
            smi:oid "1.3.6.1.2.1.88.1.2.2.1.5";
         }

         leaf mteTriggerValueID {
            type yang:object-identifier;
            config true;
            description   
              "The object identifier of the MIB object to sample to see
               if the trigger should fire.
               
               This may be wildcarded by truncating all or part of the
               instance portion, in which case the value is obtained
               as if with a GetNext function, checking multiple values
               
               
               if they exist.  If such wildcarding is applied,
               mteTriggerValueIDWildcard must be 'true' and if not it must
               be 'false'.
               
               Bad object identifiers or a mismatch between truncating the
               identifier and the value of mteTriggerValueIDWildcard result
               in operation as one would expect when providing the wrong
               identifier to a Get or GetNext operation.  The Get will fail
               or get the wrong object.  The GetNext will indeed get whatever
               is next, proceeding until it runs past the initial part of the
               identifier and perhaps many unintended objects for confusing
               results.  If the value syntax of those objects is not usable,
               that results in a 'badType' error that terminates the scan.
               
               Each instance that fills the wildcard is independent of any
               additional instances, that is, wildcarded objects operate
               as if there were a separate table entry for each instance
               that fills the wildcard without having to actually predict
               all possible instances ahead of time.";
            smi:default "zeroDotZero";
            smi:oid "1.3.6.1.2.1.88.1.2.2.1.6";
         }

         leaf mteTriggerValueIDWildcard {
            type smiv2:TruthValue;
            config true;
            description   
              "Control for whether mteTriggerValueID is to be treated as
               fully-specified or wildcarded, with 'true' indicating wildcard.";
            smi:default "false";
            smi:oid "1.3.6.1.2.1.88.1.2.2.1.7";
         }

         leaf mteTriggerTargetTag {
            type snmp-target:SnmpTagValue;
            config true;
            description   
              "The tag for the target(s) from which to obtain the condition
               for a trigger check.
               
               A length of 0 indicates the local system.  In this case,
               access to the objects indicated by mteTriggerValueID is under
               the security credentials of the requester that set
               mteTriggerEntryStatus to 'active'.  Those credentials are the
               input parameters for isAccessAllowed from the Architecture for
               Describing SNMP Management Frameworks.
               
               Otherwise access rights are checked according to the security
               
               
               parameters resulting from the tag.";
            smi:default "";
            smi:oid "1.3.6.1.2.1.88.1.2.2.1.8";
         }

         leaf mteTriggerContextName {
            type snmp-framework:SnmpAdminString;
            config true;
            description   
              "The management context from which to obtain mteTriggerValueID.
               
               This may be wildcarded by leaving characters off the end.  For
               example use 'Repeater' to wildcard to 'Repeater1',
               'Repeater2', 'Repeater-999.87b', and so on.  To indicate such
               wildcarding is intended, mteTriggerContextNameWildcard must
               be 'true'.
               
               Each instance that fills the wildcard is independent of any
               additional instances, that is, wildcarded objects operate
               as if there were a separate table entry for each instance
               that fills the wildcard without having to actually predict
               all possible instances ahead of time.
               
               Operation of this feature assumes that the local system has a
               list of available contexts against which to apply the
               wildcard.  If the objects are being read from the local
               system, this is clearly the system's own list of contexts.
               For a remote system a local version of such a list is not
               defined by any current standard and may not be available, so
               this function MAY not be supported.";
            smi:default "";
            smi:oid "1.3.6.1.2.1.88.1.2.2.1.9";
         }

         leaf mteTriggerContextNameWildcard {
            type smiv2:TruthValue;
            config true;
            description   
              "Control for whether mteTriggerContextName is to be treated as
               fully-specified or wildcarded, with 'true' indicating wildcard.";
            smi:default "false";
            smi:oid "1.3.6.1.2.1.88.1.2.2.1.10";
         }

         leaf mteTriggerFrequency {
            type uint32;
            units "seconds";
            config true;
            description   
              "The number of seconds to wait between trigger samples.  To
               encourage consistency in sampling, the interval is measured
               from the beginning of one check to the beginning of the next
               and the timer is restarted immediately when it expires, not
               when the check completes.
               
               If the next sample begins before the previous one completed the
               system may either attempt to make the check or treat this as an
               error condition with the error 'sampleOverrun'.
               
               A frequency of 0 indicates instantaneous recognition of the
               condition.  This is not possible in many cases, but may
               be supported in cases where it makes sense and the system is
               able to do so.  This feature allows the MIB to be used in
               implementations where such interrupt-driven behavior is
               possible and is not likely to be supported for all MIB objects
               even then since such sampling generally has to be tightly
               integrated into low-level code.
               
               Systems that can support this SHOULD document those cases
               where it can be used.  In cases where it can not, setting this
               object to 0 should be disallowed.";
            smi:default "600";
            smi:oid "1.3.6.1.2.1.88.1.2.2.1.11";
         }

         leaf mteTriggerObjectsOwner {
            type snmp-framework:SnmpAdminString {
               length "0..32";
            }
            config true;
            description   
              "To go with mteTriggerObjects, the mteOwner of a group of
               objects from mteObjectsTable.";
            smi:default "";
            smi:oid "1.3.6.1.2.1.88.1.2.2.1.12";
         }

         leaf mteTriggerObjects {
            type snmp-framework:SnmpAdminString {
               length "0..32";
            }
            config true;
            description   
              "The mteObjectsName of a group of objects from
               mteObjectsTable.  These objects are to be added to any
               Notification resulting from the firing of this trigger.
               
               A list of objects may also be added based on the event or on
               the value of mteTriggerTest.
               
               
               
               A length of 0 indicates no additional objects.";
            smi:default "";
            smi:oid "1.3.6.1.2.1.88.1.2.2.1.13";
         }

         leaf mteTriggerEnabled {
            type smiv2:TruthValue;
            config true;
            description   
              "A control to allow a trigger to be configured but not used.
               When the value is 'false' the trigger is not sampled.";
            smi:default "false";
            smi:oid "1.3.6.1.2.1.88.1.2.2.1.14";
         }

         leaf mteTriggerEntryStatus {
            type smiv2:RowStatus;
            config true;
            description   
              "The control that allows creation and deletion of entries.
               Once made active an entry may not be modified except to
               delete it.";
            smi:oid "1.3.6.1.2.1.88.1.2.2.1.15";
         }
      }


      /* XXX table comments here XXX */

      list mteTriggerDeltaEntry {

         key "mteOwner mteTriggerName";
         description 
           "Information about a single trigger's delta sampling.  Entries
            automatically exist in this this table for each mteTriggerEntry
            that has mteTriggerSampleType set to 'deltaValue'.";
         smi:oid "1.3.6.1.2.1.88.1.2.3.1";

         leaf mteOwner {
            type leafref {
               path "/disman-event:mteTrigger/disman-event:mteTriggerEntry/disman-event:mteOwner";
            }
            config true;
            description   
              "Automagically generated leafref leaf.";
         }
         leaf mteTriggerName {
            type leafref {
               path "/disman-event:mteTrigger/disman-event:mteTriggerEntry/disman-event:mteTriggerName";
            }
            config true;
            description   
              "Automagically generated leafref leaf.";
         }

         leaf mteTriggerDeltaDiscontinuityID {
            type yang:object-identifier;
            config true;
            description   
              "The OBJECT IDENTIFIER (OID) of a TimeTicks, TimeStamp, or
               DateAndTime object that indicates a discontinuity in the value
               at mteTriggerValueID.
               
               The OID may be for a leaf object (e.g. sysUpTime.0) or may
               be wildcarded to match mteTriggerValueID.
               
               This object supports normal checking for a discontinuity in a
               counter.  Note that if this object does not point to sysUpTime
               discontinuity checking MUST still check sysUpTime for an overall
               discontinuity.
               
               If the object identified is not accessible the sample attempt
               is in error, with the error code as from an SNMP request.
               
               Bad object identifiers or a mismatch between truncating the
               identifier and the value of mteDeltaDiscontinuityIDWildcard
               result in operation as one would expect when providing the
               wrong identifier to a Get operation.  The Get will fail or get
               the wrong object.  If the value syntax of those objects is not
               usable, that results in an error that terminates the sample
               with a 'badType' error code.";
            smi:default "sysUpTimeInstance";
            smi:oid "1.3.6.1.2.1.88.1.2.3.1.1";
         }

         leaf mteTriggerDeltaDiscontinuityIDWildcard {
            type smiv2:TruthValue;
            config true;
            description   
              "Control for whether mteTriggerDeltaDiscontinuityID is to be
               treated as fully-specified or wildcarded, with 'true'
               indicating wildcard. Note that the value of this object will
               be the same as that of the corresponding instance of
               mteTriggerValueIDWildcard when the corresponding
               
               
               mteTriggerSampleType is 'deltaValue'.";
            smi:default "false";
            smi:oid "1.3.6.1.2.1.88.1.2.3.1.2";
         }

         leaf mteTriggerDeltaDiscontinuityIDType {
            type enumeration {
               enum timeTicks   { value 1; }
               enum timeStamp   { value 2; }
               enum dateAndTime { value 3; }
            }
            config true;
            description   
              "The value 'timeTicks' indicates the
               mteTriggerDeltaDiscontinuityID of this row is of syntax
               TimeTicks.  The value 'timeStamp' indicates syntax TimeStamp.
               The value 'dateAndTime' indicates syntax DateAndTime.";
            smi:default "timeTicks";
            smi:oid "1.3.6.1.2.1.88.1.2.3.1.3";
         }
      }


      /* XXX table comments here XXX */

      list mteTriggerExistenceEntry {

         key "mteOwner mteTriggerName";
         description 
           "Information about a single existence trigger.  Entries
            automatically exist in this this table for each mteTriggerEntry
            that has 'existence' set in mteTriggerTest.";
         smi:oid "1.3.6.1.2.1.88.1.2.4.1";

         leaf mteOwner {
            type leafref {
               path "/disman-event:mteTrigger/disman-event:mteTriggerEntry/disman-event:mteOwner";
            }
            config true;
            description   
              "Automagically generated leafref leaf.";
         }
         leaf mteTriggerName {
            type leafref {
               path "/disman-event:mteTrigger/disman-event:mteTriggerEntry/disman-event:mteTriggerName";
            }
            config true;
            description   
              "Automagically generated leafref leaf.";
         }

         leaf mteTriggerExistenceTest {
            type bits {
               bit present { position 0; }
               bit absent  { position 1; }
               bit changed { position 2; }
            }
            config true;
            description   
              "The type of existence test to perform.  The trigger fires
               when the object at mteTriggerValueID is seen to go from
               present to absent, from absent to present, or to have it's
               value changed, depending on which tests are selected:
               
               present(0) - when this test is selected, the trigger fires
               when the mteTriggerValueID object goes from absent to present.
               
               absent(1)  - when this test is selected, the trigger fires
               when the mteTriggerValueID object goes from present to absent.
               changed(2) - when this test is selected, the trigger fires
               the mteTriggerValueID object value changes.
               
               Once the trigger has fired for either presence or absence it
               will not fire again for that state until the object has been
               to the other state. ";
            smi:default "7)";
            smi:oid "1.3.6.1.2.1.88.1.2.4.1.1";
         }

         leaf mteTriggerExistenceStartup {
            type bits {
               bit present { position 0; }
               bit absent  { position 1; }
            }
            config true;
            description   
              "Control for whether an event may be triggered when this entry
               is first set to 'active' and the test specified by
               mteTriggerExistenceTest is true.  Setting an option causes
               that trigger to fire when its test is true.";
            smi:default "7)";
            smi:oid "1.3.6.1.2.1.88.1.2.4.1.2";
         }

         leaf mteTriggerExistenceObjectsOwner {
            type snmp-framework:SnmpAdminString {
               length "0..32";
            }
            config true;
            description   
              "To go with mteTriggerExistenceObjects, the mteOwner of a
               group of objects from mteObjectsTable.";
            smi:default "";
            smi:oid "1.3.6.1.2.1.88.1.2.4.1.3";
         }

         leaf mteTriggerExistenceObjects {
            type snmp-framework:SnmpAdminString {
               length "0..32";
            }
            config true;
            description   
              "The mteObjectsName of a group of objects from
               mteObjectsTable.  These objects are to be added to any
               Notification resulting from the firing of this trigger for
               this test.
               
               A list of objects may also be added based on the overall
               trigger, the event or other settings in mteTriggerTest.
               
               A length of 0 indicates no additional objects.";
            smi:default "";
            smi:oid "1.3.6.1.2.1.88.1.2.4.1.4";
         }

         leaf mteTriggerExistenceEventOwner {
            type snmp-framework:SnmpAdminString {
               length "0..32";
            }
            config true;
            description   
              "To go with mteTriggerExistenceEvent, the mteOwner of an event
               entry from the mteEventTable.";
            smi:default "";
            smi:oid "1.3.6.1.2.1.88.1.2.4.1.5";
         }

         leaf mteTriggerExistenceEvent {
            type snmp-framework:SnmpAdminString {
               length "0..32";
            }
            config true;
            description   
              "The mteEventName of the event to invoke when mteTriggerType is
               'existence' and this trigger fires.  A length of 0 indicates no
               event.";
            smi:default "";
            smi:oid "1.3.6.1.2.1.88.1.2.4.1.6";
         }
      }


      /* XXX table comments here XXX */

      list mteTriggerBooleanEntry {

         key "mteOwner mteTriggerName";
         description 
           "Information about a single boolean trigger.  Entries
            automatically exist in this this table for each mteTriggerEntry
            that has 'boolean' set in mteTriggerTest.";
         smi:oid "1.3.6.1.2.1.88.1.2.5.1";

         leaf mteOwner {
            type leafref {
               path "/disman-event:mteTrigger/disman-event:mteTriggerEntry/disman-event:mteOwner";
            }
            config true;
            description   
              "Automagically generated leafref leaf.";
         }
         leaf mteTriggerName {
            type leafref {
               path "/disman-event:mteTrigger/disman-event:mteTriggerEntry/disman-event:mteTriggerName";
            }
            config true;
            description   
              "Automagically generated leafref leaf.";
         }

         leaf mteTriggerBooleanComparison {
            type enumeration {
               enum unequal        { value 1; }
               enum equal          { value 2; }
               enum less           { value 3; }
               enum lessOrEqual    { value 4; }
               enum greater        { value 5; }
               enum greaterOrEqual { value 6; }
            }
            config true;
            description   
              "The type of boolean comparison to perform.
               
               The value at mteTriggerValueID is compared to
               mteTriggerBooleanValue, so for example if
               mteTriggerBooleanComparison is 'less' the result would be true
               if the value at mteTriggerValueID is less than the value of
               mteTriggerBooleanValue.";
            smi:default "unequal";
            smi:oid "1.3.6.1.2.1.88.1.2.5.1.1";
         }

         leaf mteTriggerBooleanValue {
            type int32;
            config true;
            description   
              "The value to use for the test specified by
               mteTriggerBooleanTest.";
            smi:default "0";
            smi:oid "1.3.6.1.2.1.88.1.2.5.1.2";
         }

         leaf mteTriggerBooleanStartup {
            type smiv2:TruthValue;
            config true;
            description   
              "Control for whether an event may be triggered when this entry
               is first set to 'active' or a new instance of the object at
               mteTriggerValueID is found and the test specified by
               mteTriggerBooleanComparison is true.  In that case an event is
               triggered if mteTriggerBooleanStartup is 'true'.";
            smi:default "true";
            smi:oid "1.3.6.1.2.1.88.1.2.5.1.3";
         }

         leaf mteTriggerBooleanObjectsOwner {
            type snmp-framework:SnmpAdminString {
               length "0..32";
            }
            config true;
            description   
              "To go with mteTriggerBooleanObjects, the mteOwner of a group
               of objects from mteObjectsTable.";
            smi:default "";
            smi:oid "1.3.6.1.2.1.88.1.2.5.1.4";
         }

         leaf mteTriggerBooleanObjects {
            type snmp-framework:SnmpAdminString {
               length "0..32";
            }
            config true;
            description   
              "The mteObjectsName of a group of objects from
               mteObjectsTable.  These objects are to be added to any
               Notification resulting from the firing of this trigger for
               this test.
               
               A list of objects may also be added based on the overall
               trigger, the event or other settings in mteTriggerTest.
               
               A length of 0 indicates no additional objects.";
            smi:default "";
            smi:oid "1.3.6.1.2.1.88.1.2.5.1.5";
         }

         leaf mteTriggerBooleanEventOwner {
            type snmp-framework:SnmpAdminString {
               length "0..32";
            }
            config true;
            description   
              "To go with mteTriggerBooleanEvent, the mteOwner of an event
               entry from mteEventTable.";
            smi:default "";
            smi:oid "1.3.6.1.2.1.88.1.2.5.1.6";
         }

         leaf mteTriggerBooleanEvent {
            type snmp-framework:SnmpAdminString {
               length "0..32";
            }
            config true;
            description   
              "The mteEventName of the event to invoke when mteTriggerType is
               'boolean' and this trigger fires.  A length of 0 indicates no
               event.";
            smi:default "";
            smi:oid "1.3.6.1.2.1.88.1.2.5.1.7";
         }
      }


      /* XXX table comments here XXX */

      list mteTriggerThresholdEntry {

         key "mteOwner mteTriggerName";
         description 
           "Information about a single threshold trigger.  Entries
            automatically exist in this table for each mteTriggerEntry
            that has 'threshold' set in mteTriggerTest.";
         smi:oid "1.3.6.1.2.1.88.1.2.6.1";

         leaf mteOwner {
            type leafref {
               path "/disman-event:mteTrigger/disman-event:mteTriggerEntry/disman-event:mteOwner";
            }
            config true;
            description   
              "Automagically generated leafref leaf.";
         }
         leaf mteTriggerName {
            type leafref {
               path "/disman-event:mteTrigger/disman-event:mteTriggerEntry/disman-event:mteTriggerName";
            }
            config true;
            description   
              "Automagically generated leafref leaf.";
         }

         leaf mteTriggerThresholdStartup {
            type enumeration {
               enum rising          { value 1; }
               enum falling         { value 2; }
               enum risingOrFalling { value 3; }
            }
            config true;
            description   
              "The event that may be triggered when this entry is first
               set to 'active' and a new instance of the object at
               mteTriggerValueID is found.  If the first sample after this
               instance becomes active is greater than or equal to
               mteTriggerThresholdRising and mteTriggerThresholdStartup is
               equal to 'rising' or 'risingOrFalling', then one
               mteTriggerThresholdRisingEvent is triggered for that instance.
               If the first sample after this entry becomes active is less
               than or equal to mteTriggerThresholdFalling and
               mteTriggerThresholdStartup is equal to 'falling' or
               'risingOrFalling', then one mteTriggerThresholdRisingEvent is
               triggered for that instance.";
            smi:default "risingOrFalling";
            smi:oid "1.3.6.1.2.1.88.1.2.6.1.1";
         }

         leaf mteTriggerThresholdRising {
            type int32;
            config true;
            description   
              "A threshold value to check against if mteTriggerType is
               'threshold'.
               
               When the current sampled value is greater than or equal to
               this threshold, and the value at the last sampling interval
               was less than this threshold, one
               mteTriggerThresholdRisingEvent is triggered.  That event is
               also triggered if the first sample after this entry becomes
               active is greater than or equal to this threshold and
               mteTriggerThresholdStartup is equal to 'rising' or
               'risingOrFalling'.
               
               After a rising event is generated, another such event is not
               triggered until the sampled value falls below this threshold
               and reaches mteTriggerThresholdFalling.";
            smi:default "0";
            smi:oid "1.3.6.1.2.1.88.1.2.6.1.2";
         }

         leaf mteTriggerThresholdFalling {
            type int32;
            config true;
            description   
              "A threshold value to check against if mteTriggerType is
               'threshold'.
               
               When the current sampled value is less than or equal to this
               threshold, and the value at the last sampling interval was
               greater than this threshold, one
               mteTriggerThresholdFallingEvent is triggered.  That event is
               also triggered if the first sample after this entry becomes
               active is less than or equal to this threshold and
               mteTriggerThresholdStartup is equal to 'falling' or
               'risingOrFalling'.
               
               After a falling event is generated, another such event is not
               triggered until the sampled value rises above this threshold
               and reaches mteTriggerThresholdRising.";
            smi:default "0";
            smi:oid "1.3.6.1.2.1.88.1.2.6.1.3";
         }

         leaf mteTriggerThresholdDeltaRising {
            type int32;
            config true;
            description   
              "A threshold value to check against if mteTriggerType is
               'threshold'.
               
               When the delta value (difference) between the current sampled
               value (value(n)) and the previous sampled value (value(n-1))
               is greater than or equal to this threshold,
               and the delta value calculated at the last sampling interval
               (i.e. value(n-1) - value(n-2)) was less than this threshold,
               one mteTriggerThresholdDeltaRisingEvent is triggered. That event
               is also triggered if the first delta value calculated after this
               entry becomes active, i.e. value(2) - value(1), where value(1)
               is the first sample taken of that instance, is greater than or
               equal to this threshold.
               
               After a rising event is generated, another such event is not
               triggered until the delta value falls below this threshold and
               reaches mteTriggerThresholdDeltaFalling.";
            smi:default "0";
            smi:oid "1.3.6.1.2.1.88.1.2.6.1.4";
         }

         leaf mteTriggerThresholdDeltaFalling {
            type int32;
            config true;
            description   
              "A threshold value to check against if mteTriggerType is
               'threshold'.
               
               When the delta value (difference) between the current sampled
               value (value(n)) and the previous sampled value (value(n-1))
               is less than or equal to this threshold,
               and the delta value calculated at the last sampling interval
               (i.e. value(n-1) - value(n-2)) was greater than this threshold,
               one mteTriggerThresholdDeltaFallingEvent is triggered. That event
               is also triggered if the first delta value calculated after this
               entry becomes active, i.e. value(2) - value(1), where value(1)
               is the first sample taken of that instance, is less than or
               equal to this threshold.
               
               After a falling event is generated, another such event is not
               triggered until the delta value falls below this threshold and
               reaches mteTriggerThresholdDeltaRising.";
            smi:default "0";
            smi:oid "1.3.6.1.2.1.88.1.2.6.1.5";
         }

         leaf mteTriggerThresholdObjectsOwner {
            type snmp-framework:SnmpAdminString {
               length "0..32";
            }
            config true;
            description   
              "To go with mteTriggerThresholdObjects, the mteOwner of a group
               of objects from mteObjectsTable.";
            smi:default "";
            smi:oid "1.3.6.1.2.1.88.1.2.6.1.6";
         }

         leaf mteTriggerThresholdObjects {
            type snmp-framework:SnmpAdminString {
               length "0..32";
            }
            config true;
            description   
              "The mteObjectsName of a group of objects from
               mteObjectsTable.  These objects are to be added to any
               Notification resulting from the firing of this trigger for
               this test.
               
               A list of objects may also be added based on the overall
               
               
               trigger, the event or other settings in mteTriggerTest.
               
               A length of 0 indicates no additional objects.";
            smi:default "";
            smi:oid "1.3.6.1.2.1.88.1.2.6.1.7";
         }

         leaf mteTriggerThresholdRisingEventOwner {
            type snmp-framework:SnmpAdminString {
               length "0..32";
            }
            config true;
            description   
              "To go with mteTriggerThresholdRisingEvent, the mteOwner of an
               event entry from mteEventTable.";
            smi:default "";
            smi:oid "1.3.6.1.2.1.88.1.2.6.1.8";
         }

         leaf mteTriggerThresholdRisingEvent {
            type snmp-framework:SnmpAdminString {
               length "0..32";
            }
            config true;
            description   
              "The mteEventName of the event to invoke when mteTriggerType is
               'threshold' and this trigger fires based on
               mteTriggerThresholdRising.  A length of 0 indicates no event.";
            smi:default "";
            smi:oid "1.3.6.1.2.1.88.1.2.6.1.9";
         }

         leaf mteTriggerThresholdFallingEventOwner {
            type snmp-framework:SnmpAdminString {
               length "0..32";
            }
            config true;
            description   
              "To go with mteTriggerThresholdFallingEvent, the mteOwner of an
               event entry from mteEventTable.";
            smi:default "";
            smi:oid "1.3.6.1.2.1.88.1.2.6.1.10";
         }

         leaf mteTriggerThresholdFallingEvent {
            type snmp-framework:SnmpAdminString {
               length "0..32";
            }
            config true;
            description   
              "The mteEventName of the event to invoke when mteTriggerType is
               'threshold' and this trigger fires based on
               mteTriggerThresholdFalling.  A length of 0 indicates no event.";
            smi:default "";
            smi:oid "1.3.6.1.2.1.88.1.2.6.1.11";
         }

         leaf mteTriggerThresholdDeltaRisingEventOwner {
            type snmp-framework:SnmpAdminString {
               length "0..32";
            }
            config true;
            description   
              "To go with mteTriggerThresholdDeltaRisingEvent, the mteOwner
               of an event entry from mteEventTable.";
            smi:default "";
            smi:oid "1.3.6.1.2.1.88.1.2.6.1.12";
         }

         leaf mteTriggerThresholdDeltaRisingEvent {
            type snmp-framework:SnmpAdminString {
               length "0..32";
            }
            config true;
            description   
              "The mteEventName of the event to invoke when mteTriggerType is
               'threshold' and this trigger fires based on
               mteTriggerThresholdDeltaRising. A length of 0 indicates
               no event.";
            smi:default "";
            smi:oid "1.3.6.1.2.1.88.1.2.6.1.13";
         }

         leaf mteTriggerThresholdDeltaFallingEventOwner {
            type snmp-framework:SnmpAdminString {
               length "0..32";
            }
            config true;
            description   
              "To go with mteTriggerThresholdDeltaFallingEvent, the mteOwner
               of an event entry from mteEventTable.";
            smi:default "";
            smi:oid "1.3.6.1.2.1.88.1.2.6.1.14";
         }

         leaf mteTriggerThresholdDeltaFallingEvent {
            type snmp-framework:SnmpAdminString {
               length "0..32";
            }
            config true;
            description   
              "The mteEventName of the event to invoke when mteTriggerType is
               'threshold' and this trigger fires based on
               mteTriggerThresholdDeltaFalling.  A length of 0 indicates
               no event.";
            smi:default "";
            smi:oid "1.3.6.1.2.1.88.1.2.6.1.15";
         }
      }
      smi:oid "1.3.6.1.2.1.88.1.2";
   }

   container mteObjects {


      /* XXX table comments here XXX */

      list mteObjectsEntry {

         key "mteOwner mteObjectsName mteObjectsIndex";
         description 
           "A group of objects.  Applications create and delete entries
            using mteObjectsEntryStatus.
            
            When adding objects to a notification they are added in the
            lexical order of their index in this table.  Those associated
            with a trigger come first, then trigger test, then event.";
         smi:oid "1.3.6.1.2.1.88.1.3.1.1";

         leaf mteOwner {
            type leafref {
               path "/disman-event:mteTrigger/disman-event:mteTriggerEntry/disman-event:mteOwner";
            }
            config true;
            description   
              "Automagically generated leafref leaf.";
         }

         leaf mteObjectsName {
            type snmp-framework:SnmpAdminString {
               length "1..32";
            }
            // config false;
            description   
              "A locally-unique, administratively assigned name for a group
               of objects.";
            smi:oid "1.3.6.1.2.1.88.1.3.1.1.1";
         }

         leaf mteObjectsIndex {
            type uint32 {
               range "1..4294967295";
            }
            // config false;
            description   
              "An arbitrary integer for the purpose of identifying
               individual objects within a mteObjectsName group.
               
               
               Objects within a group are placed in the notification in the
               numerical order of this index.
               
               Groups are placed in the notification in the order of the
               selections for overall trigger, trigger test, and event.
               Within trigger test they are in the same order as the
               numerical values of the bits defined for mteTriggerTest.
               
               Bad object identifiers or a mismatch between truncating the
               identifier and the value of mteDeltaDiscontinuityIDWildcard
               result in operation as one would expect when providing the
               wrong identifier to a Get operation.  The Get will fail or get
               the wrong object.  If the object is not available it is omitted
               from the notification.";
            smi:oid "1.3.6.1.2.1.88.1.3.1.1.2";
         }

         leaf mteObjectsID {
            type yang:object-identifier;
            config true;
            description   
              "The object identifier of a MIB object to add to a
               Notification that results from the firing of a trigger.
               
               This may be wildcarded by truncating all or part of the
               instance portion, in which case the instance portion of the
               OID for obtaining this object will be the same as that used
               in obtaining the mteTriggerValueID that fired.  If such
               wildcarding is applied, mteObjectsIDWildcard must be
               'true' and if not it must be 'false'.
               
               Each instance that fills the wildcard is independent of any
               additional instances, that is, wildcarded objects operate
               as if there were a separate table entry for each instance
               that fills the wildcard without having to actually predict
               all possible instances ahead of time.";
            smi:default "zeroDotZero";
            smi:oid "1.3.6.1.2.1.88.1.3.1.1.3";
         }

         leaf mteObjectsIDWildcard {
            type smiv2:TruthValue;
            config true;
            description   
              "Control for whether mteObjectsID is to be treated as
               fully-specified or wildcarded, with 'true' indicating wildcard.";
            smi:default "false";
            smi:oid "1.3.6.1.2.1.88.1.3.1.1.4";
         }

         leaf mteObjectsEntryStatus {
            type smiv2:RowStatus;
            config true;
            description   
              "The control that allows creation and deletion of entries.
               Once made active an entry MAY not be modified except to
               delete it.";
            smi:oid "1.3.6.1.2.1.88.1.3.1.1.5";
         }
      }
      smi:oid "1.3.6.1.2.1.88.1.3";
   }

   container mteEvent {

      leaf mteEventFailures {
         type yang:counter32;
         config false;
         description 
           "The number of times an attempt to invoke an event
            has failed.  This counts individually for each
            attempt in a group of targets or each attempt for a
            wildcarded trigger object.";
         smi:oid "1.3.6.1.2.1.88.1.4.1";
      }


      /* XXX table comments here XXX */

      list mteEventEntry {

         key "mteOwner mteEventName";
         description 
           "Information about a single event.  Applications create and
            delete entries using mteEventEntryStatus.";
         smi:oid "1.3.6.1.2.1.88.1.4.2.1";

         leaf mteOwner {
            type leafref {
               path "/disman-event:mteTrigger/disman-event:mteTriggerEntry/disman-event:mteOwner";
            }
            config true;
            description   
              "Automagically generated leafref leaf.";
         }

         leaf mteEventName {
            type snmp-framework:SnmpAdminString {
               length "1..32";
            }
            // config false;
            description   
              "A locally-unique, administratively assigned name for the
               event.";
            smi:oid "1.3.6.1.2.1.88.1.4.2.1.1";
         }

         leaf mteEventComment {
            type snmp-framework:SnmpAdminString;
            config true;
            description   
              "A description of the event's function and use.";
            smi:default "";
            smi:oid "1.3.6.1.2.1.88.1.4.2.1.2";
         }

         leaf mteEventActions {
            type bits {
               bit notification { position 0; }
               bit set          { position 1; }
            }
            config true;
            description   
              "The actions to perform when this event occurs.
               
               For 'notification', Traps and/or Informs are sent according
               to the configuration in the SNMP Notification MIB.
               
               For 'set', an SNMP Set operation is performed according to
               control values in this entry.";
            smi:default "()";
            smi:oid "1.3.6.1.2.1.88.1.4.2.1.3";
         }

         leaf mteEventEnabled {
            type smiv2:TruthValue;
            config true;
            description   
              "A control to allow an event to be configured but not used.
               When the value is 'false' the event does not execute even if
               
               
               triggered.";
            smi:default "false";
            smi:oid "1.3.6.1.2.1.88.1.4.2.1.4";
         }

         leaf mteEventEntryStatus {
            type smiv2:RowStatus;
            config true;
            description   
              "The control that allows creation and deletion of entries.
               Once made active an entry MAY not be modified except to
               delete it.";
            smi:oid "1.3.6.1.2.1.88.1.4.2.1.5";
         }
      }


      /* XXX table comments here XXX */

      list mteEventNotificationEntry {

         key "mteOwner mteEventName";
         description 
           "Information about a single event's notification.  Entries
            automatically exist in this this table for each mteEventEntry
            that has 'notification' set in mteEventActions.";
         smi:oid "1.3.6.1.2.1.88.1.4.3.1";

         leaf mteOwner {
            type leafref {
               path "/disman-event:mteTrigger/disman-event:mteTriggerEntry/disman-event:mteOwner";
            }
            config true;
            description   
              "Automagically generated leafref leaf.";
         }
         leaf mteEventName {
            type leafref {
               path "/disman-event:mteEvent/disman-event:mteEventEntry/disman-event:mteEventName";
            }
            config true;
            description   
              "Automagically generated leafref leaf.";
         }

         leaf mteEventNotification {
            type yang:object-identifier;
            config true;
            description   
              "The object identifier from the NOTIFICATION-TYPE for the
               notification to use if metEventActions has 'notification' set.";
            smi:default "zeroDotZero";
            smi:oid "1.3.6.1.2.1.88.1.4.3.1.1";
         }

         leaf mteEventNotificationObjectsOwner {
            type snmp-framework:SnmpAdminString {
               length "0..32";
            }
            config true;
            description   
              "To go with mteEventNotificationObjects, the mteOwner of a
               group of objects from mteObjectsTable.";
            smi:default "";
            smi:oid "1.3.6.1.2.1.88.1.4.3.1.2";
         }

         leaf mteEventNotificationObjects {
            type snmp-framework:SnmpAdminString {
               length "0..32";
            }
            config true;
            description   
              "The mteObjectsName of a group of objects from
               mteObjectsTable if mteEventActions has 'notification' set.
               These objects are to be added to any Notification generated by
               this event.
               
               Objects may also be added based on the trigger that stimulated
               the event.
               
               A length of 0 indicates no additional objects.";
            smi:default "";
            smi:oid "1.3.6.1.2.1.88.1.4.3.1.3";
         }
      }


      /* XXX table comments here XXX */

      list mteEventSetEntry {

         key "mteOwner mteEventName";
         description 
           "Information about a single event's set option.  Entries
            automatically exist in this this table for each mteEventEntry
            that has 'set' set in mteEventActions.";
         smi:oid "1.3.6.1.2.1.88.1.4.4.1";

         leaf mteOwner {
            type leafref {
               path "/disman-event:mteTrigger/disman-event:mteTriggerEntry/disman-event:mteOwner";
            }
            config true;
            description   
              "Automagically generated leafref leaf.";
         }
         leaf mteEventName {
            type leafref {
               path "/disman-event:mteEvent/disman-event:mteEventEntry/disman-event:mteEventName";
            }
            config true;
            description   
              "Automagically generated leafref leaf.";
         }

         leaf mteEventSetObject {
            type yang:object-identifier;
            config true;
            description   
              "The object identifier from the MIB object to set if
               mteEventActions has 'set' set.
               
               This object identifier may be wildcarded by leaving
               sub-identifiers off the end, in which case
               nteEventSetObjectWildCard must be 'true'.
               
               If mteEventSetObject is wildcarded the instance used to set the
               object to which it points is the same as the instance from the
               value of mteTriggerValueID that triggered the event.
               
               Each instance that fills the wildcard is independent of any
               additional instances, that is, wildcarded objects operate
               as if there were a separate table entry for each instance
               that fills the wildcard without having to actually predict
               all possible instances ahead of time.
               
               Bad object identifiers or a mismatch between truncating the
               identifier and the value of mteSetObjectWildcard
               result in operation as one would expect when providing the
               wrong identifier to a Set operation.  The Set will fail or set
               the wrong object.  If the value syntax of the destination
               object is not correct, the Set fails with the normal SNMP
               error code.";
            smi:default "zeroDotZero";
            smi:oid "1.3.6.1.2.1.88.1.4.4.1.1";
         }

         leaf mteEventSetObjectWildcard {
            type smiv2:TruthValue;
            config true;
            description   
              "Control over whether mteEventSetObject is to be treated as
               fully-specified or wildcarded, with 'true' indicating wildcard
               if mteEventActions has 'set' set.";
            smi:default "false";
            smi:oid "1.3.6.1.2.1.88.1.4.4.1.2";
         }

         leaf mteEventSetValue {
            type int32;
            config true;
            description   
              "The value to which to set the object at mteEventSetObject
               if mteEventActions has 'set' set.";
            smi:default "0";
            smi:oid "1.3.6.1.2.1.88.1.4.4.1.3";
         }

         leaf mteEventSetTargetTag {
            type snmp-target:SnmpTagValue;
            config true;
            description   
              "The tag for the target(s) at which to set the object at
               mteEventSetObject to mteEventSetValue if mteEventActions
               has 'set' set.
               
               Systems limited to self management MAY reject a non-zero
               length for the value of this object.
               
               A length of 0 indicates the local system.  In this case,
               access to the objects indicated by mteEventSetObject is under
               the security credentials of the requester that set
               mteTriggerEntryStatus to 'active'.  Those credentials are the
               input parameters for isAccessAllowed from the Architecture for
               Describing SNMP Management Frameworks.
               
               Otherwise access rights are checked according to the security
               parameters resulting from the tag.";
            smi:default "";
            smi:oid "1.3.6.1.2.1.88.1.4.4.1.4";
         }

         leaf mteEventSetContextName {
            type snmp-framework:SnmpAdminString;
            config true;
            description   
              "The management context in which to set mteEventObjectID.
               if mteEventActions has 'set' set.
               
               This may be wildcarded by leaving characters off the end.  To
               indicate such wildcarding mteEventSetContextNameWildcard must
               be 'true'.
               
               If this context name is wildcarded the value used to complete
               the wildcarding of mteTriggerContextName will be appended.";
            smi:default "";
            smi:oid "1.3.6.1.2.1.88.1.4.4.1.5";
         }

         leaf mteEventSetContextNameWildcard {
            type smiv2:TruthValue;
            config true;
            description   
              "Control for whether mteEventSetContextName is to be treated as
               fully-specified or wildcarded, with 'true' indicating wildcard
               if mteEventActions has 'set' set.";
            smi:default "false";
            smi:oid "1.3.6.1.2.1.88.1.4.4.1.6";
         }
      }
      smi:oid "1.3.6.1.2.1.88.1.4";
   }

   container dismanEventMIBNotificationObjects {

      leaf mteHotTrigger {
         type snmp-framework:SnmpAdminString;
         config false;
         description 
           "The name of the trigger causing the notification.";
         smi:oid "1.3.6.1.2.1.88.2.1.1";
      }

      leaf mteHotTargetName {
         type snmp-framework:SnmpAdminString;
         config false;
         description 
           "The SNMP Target MIB's snmpTargetAddrName related to the
            notification.";
         smi:oid "1.3.6.1.2.1.88.2.1.2";
      }

      leaf mteHotContextName {
         type snmp-framework:SnmpAdminString;
         config false;
         description 
           "The context name related to the notification.  This MUST be as
            fully-qualified as possible, including filling in wildcard
            information determined in processing.";
         smi:oid "1.3.6.1.2.1.88.2.1.3";
      }

      leaf mteHotOID {
         type yang:object-identifier;
         config false;
         description 
           "The object identifier of the destination object related to the
            notification.  This MUST be as fully-qualified as possible,
            including filling in wildcard information determined in
            processing.
            
            For a trigger-related notification this is from
            mteTriggerValueID.
            
            For a set failure this is from mteEventSetObject.";
         smi:oid "1.3.6.1.2.1.88.2.1.4";
      }

      leaf mteHotValue {
         type int32;
         config false;
         description 
           "The value of the object at mteTriggerValueID when a
            trigger fired.";
         smi:oid "1.3.6.1.2.1.88.2.1.5";
      }

      leaf mteFailedReason {
         type disman-event:FailureReason;
         config false;
         description 
           "The reason for the failure of an attempt to check for a
            trigger condition or set an object in response to an event.";
         smi:oid "1.3.6.1.2.1.88.2.1.6";
      }
      smi:oid "1.3.6.1.2.1.88.2.1";
   }

   notification mteTriggerFired {
      description   
        "Notification that the trigger indicated by the object
         instances has fired, for triggers with mteTriggerType
         'boolean' or 'existence'.";
      smi:oid "1.3.6.1.2.1.88.2.0.1";

      container mteTriggerFired-mteHotTrigger {
         leaf mteHotTrigger {
            type snmp-framework:SnmpAdminString;
            config false;
            description   
              "The name of the trigger causing the notification.";
            smi:oid "1.3.6.1.2.1.88.2.1.1";
         }
      }

      container mteTriggerFired-mteHotTargetName {
         leaf mteHotTargetName {
            type snmp-framework:SnmpAdminString;
            config false;
            description   
              "The SNMP Target MIB's snmpTargetAddrName related to the
               notification.";
            smi:oid "1.3.6.1.2.1.88.2.1.2";
         }
      }

      container mteTriggerFired-mteHotContextName {
         leaf mteHotContextName {
            type snmp-framework:SnmpAdminString;
            config false;
            description   
              "The context name related to the notification.  This MUST be as
               fully-qualified as possible, including filling in wildcard
               information determined in processing.";
            smi:oid "1.3.6.1.2.1.88.2.1.3";
         }
      }

      container mteTriggerFired-mteHotOID {
         leaf mteHotOID {
            type yang:object-identifier;
            config false;
            description   
              "The object identifier of the destination object related to the
               notification.  This MUST be as fully-qualified as possible,
               including filling in wildcard information determined in
               processing.
               
               For a trigger-related notification this is from
               mteTriggerValueID.
               
               For a set failure this is from mteEventSetObject.";
            smi:oid "1.3.6.1.2.1.88.2.1.4";
         }
      }

      container mteTriggerFired-mteHotValue {
         leaf mteHotValue {
            type int32;
            config false;
            description   
              "The value of the object at mteTriggerValueID when a
               trigger fired.";
            smi:oid "1.3.6.1.2.1.88.2.1.5";
         }
      }

   }

   notification mteTriggerRising {
      description   
        "Notification that the rising threshold was met for triggers
         with mteTriggerType 'threshold'.";
      smi:oid "1.3.6.1.2.1.88.2.0.2";

      container mteTriggerRising-mteHotTrigger {
         leaf mteHotTrigger {
            type snmp-framework:SnmpAdminString;
            config false;
            description   
              "The name of the trigger causing the notification.";
            smi:oid "1.3.6.1.2.1.88.2.1.1";
         }
      }

      container mteTriggerRising-mteHotTargetName {
         leaf mteHotTargetName {
            type snmp-framework:SnmpAdminString;
            config false;
            description   
              "The SNMP Target MIB's snmpTargetAddrName related to the
               notification.";
            smi:oid "1.3.6.1.2.1.88.2.1.2";
         }
      }

      container mteTriggerRising-mteHotContextName {
         leaf mteHotContextName {
            type snmp-framework:SnmpAdminString;
            config false;
            description   
              "The context name related to the notification.  This MUST be as
               fully-qualified as possible, including filling in wildcard
               information determined in processing.";
            smi:oid "1.3.6.1.2.1.88.2.1.3";
         }
      }

      container mteTriggerRising-mteHotOID {
         leaf mteHotOID {
            type yang:object-identifier;
            config false;
            description   
              "The object identifier of the destination object related to the
               notification.  This MUST be as fully-qualified as possible,
               including filling in wildcard information determined in
               processing.
               
               For a trigger-related notification this is from
               mteTriggerValueID.
               
               For a set failure this is from mteEventSetObject.";
            smi:oid "1.3.6.1.2.1.88.2.1.4";
         }
      }

      container mteTriggerRising-mteHotValue {
         leaf mteHotValue {
            type int32;
            config false;
            description   
              "The value of the object at mteTriggerValueID when a
               trigger fired.";
            smi:oid "1.3.6.1.2.1.88.2.1.5";
         }
      }

   }

   notification mteTriggerFalling {
      description   
        "Notification that the falling threshold was met for triggers
         with mteTriggerType 'threshold'.";
      smi:oid "1.3.6.1.2.1.88.2.0.3";

      container mteTriggerFalling-mteHotTrigger {
         leaf mteHotTrigger {
            type snmp-framework:SnmpAdminString;
            config false;
            description   
              "The name of the trigger causing the notification.";
            smi:oid "1.3.6.1.2.1.88.2.1.1";
         }
      }

      container mteTriggerFalling-mteHotTargetName {
         leaf mteHotTargetName {
            type snmp-framework:SnmpAdminString;
            config false;
            description   
              "The SNMP Target MIB's snmpTargetAddrName related to the
               notification.";
            smi:oid "1.3.6.1.2.1.88.2.1.2";
         }
      }

      container mteTriggerFalling-mteHotContextName {
         leaf mteHotContextName {
            type snmp-framework:SnmpAdminString;
            config false;
            description   
              "The context name related to the notification.  This MUST be as
               fully-qualified as possible, including filling in wildcard
               information determined in processing.";
            smi:oid "1.3.6.1.2.1.88.2.1.3";
         }
      }

      container mteTriggerFalling-mteHotOID {
         leaf mteHotOID {
            type yang:object-identifier;
            config false;
            description   
              "The object identifier of the destination object related to the
               notification.  This MUST be as fully-qualified as possible,
               including filling in wildcard information determined in
               processing.
               
               For a trigger-related notification this is from
               mteTriggerValueID.
               
               For a set failure this is from mteEventSetObject.";
            smi:oid "1.3.6.1.2.1.88.2.1.4";
         }
      }

      container mteTriggerFalling-mteHotValue {
         leaf mteHotValue {
            type int32;
            config false;
            description   
              "The value of the object at mteTriggerValueID when a
               trigger fired.";
            smi:oid "1.3.6.1.2.1.88.2.1.5";
         }
      }

   }

   notification mteTriggerFailure {
      description   
        "Notification that an attempt to check a trigger has failed.
         
         The network manager must enable this notification only with
         a certain fear and trembling, as it can easily crowd out more
         important information.  It should be used only to help diagnose
         a problem that has appeared in the error counters and can not
         be found otherwise.";
      smi:oid "1.3.6.1.2.1.88.2.0.4";

      container mteTriggerFailure-mteHotTrigger {
         leaf mteHotTrigger {
            type snmp-framework:SnmpAdminString;
            config false;
            description   
              "The name of the trigger causing the notification.";
            smi:oid "1.3.6.1.2.1.88.2.1.1";
         }
      }

      container mteTriggerFailure-mteHotTargetName {
         leaf mteHotTargetName {
            type snmp-framework:SnmpAdminString;
            config false;
            description   
              "The SNMP Target MIB's snmpTargetAddrName related to the
               notification.";
            smi:oid "1.3.6.1.2.1.88.2.1.2";
         }
      }

      container mteTriggerFailure-mteHotContextName {
         leaf mteHotContextName {
            type snmp-framework:SnmpAdminString;
            config false;
            description   
              "The context name related to the notification.  This MUST be as
               fully-qualified as possible, including filling in wildcard
               information determined in processing.";
            smi:oid "1.3.6.1.2.1.88.2.1.3";
         }
      }

      container mteTriggerFailure-mteHotOID {
         leaf mteHotOID {
            type yang:object-identifier;
            config false;
            description   
              "The object identifier of the destination object related to the
               notification.  This MUST be as fully-qualified as possible,
               including filling in wildcard information determined in
               processing.
               
               For a trigger-related notification this is from
               mteTriggerValueID.
               
               For a set failure this is from mteEventSetObject.";
            smi:oid "1.3.6.1.2.1.88.2.1.4";
         }
      }

      container mteTriggerFailure-mteFailedReason {
         leaf mteFailedReason {
            type disman-event:FailureReason;
            config false;
            description   
              "The reason for the failure of an attempt to check for a
               trigger condition or set an object in response to an event.";
            smi:oid "1.3.6.1.2.1.88.2.1.6";
         }
      }

   }

   notification mteEventSetFailure {
      description   
        "Notification that an attempt to do a set in response to an
         event has failed.
         
         The network manager must enable this notification only with
         a certain fear and trembling, as it can easily crowd out more
         important information.  It should be used only to help diagnose
         a problem that has appeared in the error counters and can not
         be found otherwise.";
      smi:oid "1.3.6.1.2.1.88.2.0.5";

      container mteEventSetFailure-mteHotTrigger {
         leaf mteHotTrigger {
            type snmp-framework:SnmpAdminString;
            config false;
            description   
              "The name of the trigger causing the notification.";
            smi:oid "1.3.6.1.2.1.88.2.1.1";
         }
      }

      container mteEventSetFailure-mteHotTargetName {
         leaf mteHotTargetName {
            type snmp-framework:SnmpAdminString;
            config false;
            description   
              "The SNMP Target MIB's snmpTargetAddrName related to the
               notification.";
            smi:oid "1.3.6.1.2.1.88.2.1.2";
         }
      }

      container mteEventSetFailure-mteHotContextName {
         leaf mteHotContextName {
            type snmp-framework:SnmpAdminString;
            config false;
            description   
              "The context name related to the notification.  This MUST be as
               fully-qualified as possible, including filling in wildcard
               information determined in processing.";
            smi:oid "1.3.6.1.2.1.88.2.1.3";
         }
      }

      container mteEventSetFailure-mteHotOID {
         leaf mteHotOID {
            type yang:object-identifier;
            config false;
            description   
              "The object identifier of the destination object related to the
               notification.  This MUST be as fully-qualified as possible,
               including filling in wildcard information determined in
               processing.
               
               For a trigger-related notification this is from
               mteTriggerValueID.
               
               For a set failure this is from mteEventSetObject.";
            smi:oid "1.3.6.1.2.1.88.2.1.4";
         }
      }

      container mteEventSetFailure-mteFailedReason {
         leaf mteFailedReason {
            type disman-event:FailureReason;
            config false;
            description   
              "The reason for the failure of an attempt to check for a
               trigger condition or set an object in response to an event.";
            smi:oid "1.3.6.1.2.1.88.2.1.6";
         }
      }

   }
} /* end of module DISMAN-EVENT-MIB */
