/*
 * This module has been generated by smidump 0.4.6:
 *
 *      smidump -f yang --yang-smi-extensions HOST-RESOURCES-TYPES
 *
 * Do not edit. Edit the source file instead!
 */

module HOST-RESOURCES-TYPES {

   /*** NAMESPACE / PREFIX DEFINITION ***/

   namespace "urn:ietf:params:xml:ns:yang:smiv2:HOST-RESOURCES-TYPES";
   prefix "host-resources-types";

   /*** LINKAGE (IMPORTS / INCLUDES) ***/

   import HOST-RESOURCES-MIB { prefix "host-resources"; }
   import yang-smi           { prefix "smi"; }

   /*** META INFORMATION ***/

   organization     
     "IETF Host Resources MIB Working Group";

   contact          
     "Steve Waldbusser
      Postal: Lucent Technologies, Inc.
              1213 Innsbruck Dr.
              Sunnyvale, CA 94089
              USA
      Phone: 650-318-1251
      Fax:   650-318-1633
      Email: waldbusser@ins.com
      
      In addition, the Host Resources MIB mailing list is dedicated
      to discussion of this MIB. To join the mailing list, send a
      request message to hostmib-request@andrew.cmu.edu. The mailing
      list address is hostmib@andrew.cmu.edu.";

   description      
     "This MIB module registers type definitions for
      storage types, device types, and file system types.
      
      After the initial revision, this module will be
      maintained by IANA.";

   revision "2000-03-06" {
      description   
        "The original version of this module, published as RFC
         2790.";
   }

} /* end of module HOST-RESOURCES-TYPES */
