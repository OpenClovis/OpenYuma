/*
 * This module has been generated by smidump 0.4.6:
 *
 *      smidump -f yang --yang-smi-extensions EtherLike-MIB
 *
 * Do not edit. Edit the source file instead!
 */

module EtherLike-MIB {

   /*** NAMESPACE / PREFIX DEFINITION ***/

   namespace "urn:ietf:params:xml:ns:yang:smiv2:EtherLike-MIB";
   prefix "etherlike-mib";

   /*** LINKAGE (IMPORTS / INCLUDES) ***/

   import IF-MIB     { prefix "if-mib"; }
   import SNMPv2-TC  { prefix "smiv2"; }
   import yang-smi   { prefix "smi"; }
   import ietf-yang-types { prefix "yang"; }

   /*** META INFORMATION ***/

   organization     
     "IETF Ethernet Interfaces and Hub MIB
      Working Group";

   contact          
     "WG E-mail: hubmib@ietf.org
      To subscribe: hubmib-request@ietf.org
      
             Chair: Dan Romascanu
            Postal: Avaya Inc.
                    Atidum Technology Park, Bldg. 3
                    Tel Aviv 61131
                    Israel
               Tel: +972 3 645 8414
            E-mail: dromasca@avaya.com
      
           Editor: John Flick
           Postal: Hewlett-Packard Company
                   8000 Foothills Blvd. M/S 5557
                   Roseville, CA 95747-5557
                   USA
              Tel: +1 916 785 4018
              Fax: +1 916 785 1199
           E-mail: johnf@rose.hp.com";

   description      
     "The MIB module to describe generic objects for
      ethernet-like network interfaces.
      
      The following reference is used throughout this
      MIB module:
      
      [IEEE 802.3 Std] refers to:
         IEEE Std 802.3, 2002 Edition: 'IEEE Standard
      
         for Information technology -
         Telecommunications and information exchange
         between systems - Local and metropolitan
         area networks - Specific requirements -
         Part 3: Carrier sense multiple access with
         collision detection (CSMA/CD) access method
         and physical layer specifications', as
         amended by IEEE Std 802.3ae-2002:
         'Amendment: Media Access Control (MAC)
         Parameters, Physical Layer, and Management
         Parameters for 10 Gb/s Operation', August,
         2002.
      
      Of particular interest is Clause 30, '10 Mb/s,
      100 Mb/s, 1000 Mb/s, and 10 Gb/s Management'.
      
      Copyright (C) The Internet Society (2003).  This
      version of this MIB module is part of RFC 3635;
      see the RFC itself for full legal notices.";

   revision "2003-09-19" {
      description   
        "Updated to include support for 10 Gb/sec
         interfaces.  This resulted in the following
         revisions:
         
         - Updated dot3StatsAlignmentErrors and
           dot3StatsSymbolErrors DESCRIPTIONs to
           reflect behaviour at 10 Gb/s
         - Added dot3StatsRateControlAbility and
           dot3RateControlStatus for management
           of the Rate Control function in 10 Gb/s
           WAN applications
         - Added 64-bit versions of all counters
           that are used on high-speed ethernet
           interfaces
         - Added object groups to contain the new
           objects
         - Deprecated etherStatsBaseGroup and
           split into etherStatsBaseGroup2 and
           etherStatsHalfDuplexGroup, so that
           interfaces which can only operate at
           full-duplex do not need to implement
           half-duplex-only statistics
         - Deprecated dot3Compliance and replaced
           it with dot3Compliance2, which includes
           the compliance information for the new
           object groups
         
         In addition, the dot3Tests and dot3Errors
         object identities have been deprecated,
         since there is no longer a standard method
         for using them.
         
         This version published as RFC 3635.";
   }
   revision "1999-08-24" {
      description   
        "Updated to include support for 1000 Mb/sec
         interfaces and full-duplex interfaces.
         This version published as RFC 2665.";
   }
   revision "1998-06-03" {
      description   
        "Updated to include support for 100 Mb/sec
         interfaces.
         This version published as RFC 2358.";
   }
   revision "1994-02-03" {
      description   
        "Initial version, published as RFC 1650.";
   }

   container dot3 {


      /* XXX table comments here XXX */

      list dot3StatsEntry {

         key "dot3StatsIndex";
         description 
           "Statistics for a particular interface to an
            ethernet-like medium.";
         smi:oid "1.3.6.1.2.1.10.7.2.1";


         leaf dot3StatsIndex {
            type if-mib:InterfaceIndex;
            // config false;
            description   
              "An index value that uniquely identifies an
               interface to an ethernet-like medium.  The
               interface identified by a particular value of
               this index is the same interface as identified
               by the same value of ifIndex.";
            reference 
              "RFC 2863, ifIndex";
            smi:oid "1.3.6.1.2.1.10.7.2.1.1";
         }

         leaf dot3StatsAlignmentErrors {
            type yang:counter32;
            config false;
            description   
              "A count of frames received on a particular
               interface that are not an integral number of
               octets in length and do not pass the FCS check.
               
               The count represented by an instance of this
               object is incremented when the alignmentError
               status is returned by the MAC service to the
               LLC (or other MAC user). Received frames for
               which multiple error conditions pertain are,
               according to the conventions of IEEE 802.3
               Layer Management, counted exclusively according
               
               to the error status presented to the LLC.
               
               This counter does not increment for group
               encoding schemes greater than 4 bits per group.
               
               For interfaces operating at 10 Gb/s, this
               counter can roll over in less than 5 minutes if
               it is incrementing at its maximum rate.  Since
               that amount of time could be less than a
               management station's poll cycle time, in order
               to avoid a loss of information, a management
               station is advised to poll the
               dot3HCStatsAlignmentErrors object for 10 Gb/s
               or faster interfaces.
               
               Discontinuities in the value of this counter can
               occur at re-initialization of the management
               system, and at other times as indicated by the
               value of ifCounterDiscontinuityTime.";
            reference 
              "[IEEE 802.3 Std.], 30.3.1.1.7,
               aAlignmentErrors";
            smi:oid "1.3.6.1.2.1.10.7.2.1.2";
         }

         leaf dot3StatsFCSErrors {
            type yang:counter32;
            config false;
            description   
              "A count of frames received on a particular
               interface that are an integral number of octets
               in length but do not pass the FCS check.  This
               count does not include frames received with
               frame-too-long or frame-too-short error.
               
               The count represented by an instance of this
               object is incremented when the frameCheckError
               status is returned by the MAC service to the
               LLC (or other MAC user). Received frames for
               which multiple error conditions pertain are,
               according to the conventions of IEEE 802.3
               Layer Management, counted exclusively according
               to the error status presented to the LLC.
               
               Note:  Coding errors detected by the physical
               layer for speeds above 10 Mb/s will cause the
               frame to fail the FCS check.
               
               For interfaces operating at 10 Gb/s, this
               counter can roll over in less than 5 minutes if
               
               it is incrementing at its maximum rate.  Since
               that amount of time could be less than a
               management station's poll cycle time, in order
               to avoid a loss of information, a management
               station is advised to poll the
               dot3HCStatsFCSErrors object for 10 Gb/s or
               faster interfaces.
               
               Discontinuities in the value of this counter can
               occur at re-initialization of the management
               system, and at other times as indicated by the
               value of ifCounterDiscontinuityTime.";
            reference 
              "[IEEE 802.3 Std.], 30.3.1.1.6,
               aFrameCheckSequenceErrors.";
            smi:oid "1.3.6.1.2.1.10.7.2.1.3";
         }

         leaf dot3StatsSingleCollisionFrames {
            type yang:counter32;
            config false;
            description   
              "A count of frames that are involved in a single
               collision, and are subsequently transmitted
               successfully.
               
               A frame that is counted by an instance of this
               object is also counted by the corresponding
               instance of either the ifOutUcastPkts,
               ifOutMulticastPkts, or ifOutBroadcastPkts,
               and is not counted by the corresponding
               instance of the dot3StatsMultipleCollisionFrames
               object.
               
               This counter does not increment when the
               interface is operating in full-duplex mode.
               
               Discontinuities in the value of this counter can
               occur at re-initialization of the management
               system, and at other times as indicated by the
               value of ifCounterDiscontinuityTime.";
            reference 
              "[IEEE 802.3 Std.], 30.3.1.1.3,
               aSingleCollisionFrames.";
            smi:oid "1.3.6.1.2.1.10.7.2.1.4";
         }

         leaf dot3StatsMultipleCollisionFrames {
            type yang:counter32;
            config false;
            description   
              "A count of frames that are involved in more
               
               than one collision and are subsequently
               transmitted successfully.
               
               A frame that is counted by an instance of this
               object is also counted by the corresponding
               instance of either the ifOutUcastPkts,
               ifOutMulticastPkts, or ifOutBroadcastPkts,
               and is not counted by the corresponding
               instance of the dot3StatsSingleCollisionFrames
               object.
               
               This counter does not increment when the
               interface is operating in full-duplex mode.
               
               Discontinuities in the value of this counter can
               occur at re-initialization of the management
               system, and at other times as indicated by the
               value of ifCounterDiscontinuityTime.";
            reference 
              "[IEEE 802.3 Std.], 30.3.1.1.4,
               aMultipleCollisionFrames.";
            smi:oid "1.3.6.1.2.1.10.7.2.1.5";
         }

         leaf dot3StatsSQETestErrors {
            type yang:counter32;
            config false;
            description   
              "A count of times that the SQE TEST ERROR
               is received on a particular interface. The
               SQE TEST ERROR is set in accordance with the
               rules for verification of the SQE detection
               mechanism in the PLS Carrier Sense Function as
               described in IEEE Std. 802.3, 2000 Edition,
               section 7.2.4.6.
               
               This counter does not increment on interfaces
               operating at speeds greater than 10 Mb/s, or on
               interfaces operating in full-duplex mode.
               
               Discontinuities in the value of this counter can
               occur at re-initialization of the management
               system, and at other times as indicated by the
               value of ifCounterDiscontinuityTime.";
            reference 
              "[IEEE 802.3 Std.], 7.2.4.6, also 30.3.2.1.4,
               aSQETestErrors.";
            smi:oid "1.3.6.1.2.1.10.7.2.1.6";
         }

         leaf dot3StatsDeferredTransmissions {
            type yang:counter32;
            config false;
            description   
              "A count of frames for which the first
               transmission attempt on a particular interface
               is delayed because the medium is busy.
               
               The count represented by an instance of this
               object does not include frames involved in
               collisions.
               
               This counter does not increment when the
               interface is operating in full-duplex mode.
               
               Discontinuities in the value of this counter can
               occur at re-initialization of the management
               system, and at other times as indicated by the
               value of ifCounterDiscontinuityTime.";
            reference 
              "[IEEE 802.3 Std.], 30.3.1.1.9,
               aFramesWithDeferredXmissions.";
            smi:oid "1.3.6.1.2.1.10.7.2.1.7";
         }

         leaf dot3StatsLateCollisions {
            type yang:counter32;
            config false;
            description   
              "The number of times that a collision is
               detected on a particular interface later than
               one slotTime into the transmission of a packet.
               
               A (late) collision included in a count
               represented by an instance of this object is
               also considered as a (generic) collision for
               purposes of other collision-related
               statistics.
               
               This counter does not increment when the
               interface is operating in full-duplex mode.
               
               Discontinuities in the value of this counter can
               occur at re-initialization of the management
               system, and at other times as indicated by the
               value of ifCounterDiscontinuityTime.";
            reference 
              "[IEEE 802.3 Std.], 30.3.1.1.10,
               aLateCollisions.";
            smi:oid "1.3.6.1.2.1.10.7.2.1.8";
         }

         leaf dot3StatsExcessiveCollisions {
            type yang:counter32;
            config false;
            description   
              "A count of frames for which transmission on a
               particular interface fails due to excessive
               collisions.
               
               This counter does not increment when the
               interface is operating in full-duplex mode.
               
               Discontinuities in the value of this counter can
               occur at re-initialization of the management
               system, and at other times as indicated by the
               value of ifCounterDiscontinuityTime.";
            reference 
              "[IEEE 802.3 Std.], 30.3.1.1.11,
               aFramesAbortedDueToXSColls.";
            smi:oid "1.3.6.1.2.1.10.7.2.1.9";
         }

         leaf dot3StatsInternalMacTransmitErrors {
            type yang:counter32;
            config false;
            description   
              "A count of frames for which transmission on a
               particular interface fails due to an internal
               MAC sublayer transmit error. A frame is only
               counted by an instance of this object if it is
               not counted by the corresponding instance of
               either the dot3StatsLateCollisions object, the
               dot3StatsExcessiveCollisions object, or the
               dot3StatsCarrierSenseErrors object.
               
               The precise meaning of the count represented by
               an instance of this object is implementation-
               specific.  In particular, an instance of this
               object may represent a count of transmission
               errors on a particular interface that are not
               otherwise counted.
               
               For interfaces operating at 10 Gb/s, this
               counter can roll over in less than 5 minutes if
               it is incrementing at its maximum rate.  Since
               that amount of time could be less than a
               management station's poll cycle time, in order
               to avoid a loss of information, a management
               station is advised to poll the
               dot3HCStatsInternalMacTransmitErrors object for
               10 Gb/s or faster interfaces.
               
               Discontinuities in the value of this counter can
               
               occur at re-initialization of the management
               system, and at other times as indicated by the
               value of ifCounterDiscontinuityTime.";
            reference 
              "[IEEE 802.3 Std.], 30.3.1.1.12,
               aFramesLostDueToIntMACXmitError.";
            smi:oid "1.3.6.1.2.1.10.7.2.1.10";
         }

         leaf dot3StatsCarrierSenseErrors {
            type yang:counter32;
            config false;
            description   
              "The number of times that the carrier sense
               condition was lost or never asserted when
               attempting to transmit a frame on a particular
               interface.
               
               The count represented by an instance of this
               object is incremented at most once per
               transmission attempt, even if the carrier sense
               condition fluctuates during a transmission
               attempt.
               
               This counter does not increment when the
               interface is operating in full-duplex mode.
               
               Discontinuities in the value of this counter can
               occur at re-initialization of the management
               system, and at other times as indicated by the
               value of ifCounterDiscontinuityTime.";
            reference 
              "[IEEE 802.3 Std.], 30.3.1.1.13,
               aCarrierSenseErrors.";
            smi:oid "1.3.6.1.2.1.10.7.2.1.11";
         }

         leaf dot3StatsFrameTooLongs {
            type yang:counter32;
            config false;
            description   
              "A count of frames received on a particular
               interface that exceed the maximum permitted
               frame size.
               
               The count represented by an instance of this
               object is incremented when the frameTooLong
               status is returned by the MAC service to the
               LLC (or other MAC user). Received frames for
               which multiple error conditions pertain are,
               according to the conventions of IEEE 802.3
               Layer Management, counted exclusively according
               to the error status presented to the LLC.
               
               For interfaces operating at 10 Gb/s, this
               counter can roll over in less than 80 minutes if
               it is incrementing at its maximum rate.  Since
               that amount of time could be less than a
               management station's poll cycle time, in order
               to avoid a loss of information, a management
               station is advised to poll the
               dot3HCStatsFrameTooLongs object for 10 Gb/s
               or faster interfaces.
               
               Discontinuities in the value of this counter can
               occur at re-initialization of the management
               system, and at other times as indicated by the
               value of ifCounterDiscontinuityTime.";
            reference 
              "[IEEE 802.3 Std.], 30.3.1.1.25,
               aFrameTooLongErrors.";
            smi:oid "1.3.6.1.2.1.10.7.2.1.13";
         }

         leaf dot3StatsInternalMacReceiveErrors {
            type yang:counter32;
            config false;
            description   
              "A count of frames for which reception on a
               particular interface fails due to an internal
               MAC sublayer receive error. A frame is only
               counted by an instance of this object if it is
               not counted by the corresponding instance of
               either the dot3StatsFrameTooLongs object, the
               dot3StatsAlignmentErrors object, or the
               dot3StatsFCSErrors object.
               
               The precise meaning of the count represented by
               an instance of this object is implementation-
               specific.  In particular, an instance of this
               object may represent a count of receive errors
               on a particular interface that are not
               otherwise counted.
               
               For interfaces operating at 10 Gb/s, this
               counter can roll over in less than 5 minutes if
               
               it is incrementing at its maximum rate.  Since
               that amount of time could be less than a
               management station's poll cycle time, in order
               to avoid a loss of information, a management
               station is advised to poll the
               dot3HCStatsInternalMacReceiveErrors object for
               10 Gb/s or faster interfaces.
               
               Discontinuities in the value of this counter can
               occur at re-initialization of the management
               system, and at other times as indicated by the
               value of ifCounterDiscontinuityTime.";
            reference 
              "[IEEE 802.3 Std.], 30.3.1.1.15,
               aFramesLostDueToIntMACRcvError.";
            smi:oid "1.3.6.1.2.1.10.7.2.1.16";
         }

         leaf dot3StatsEtherChipSet {
            type yang:object-identifier;
            config false;
            status deprecated;
            description   
              "******** THIS OBJECT IS DEPRECATED ********
               
               This object contains an OBJECT IDENTIFIER
               which identifies the chipset used to
               realize the interface. Ethernet-like
               interfaces are typically built out of
               several different chips. The MIB implementor
               is presented with a decision of which chip
               to identify via this object. The implementor
               should identify the chip which is usually
               called the Medium Access Control chip.
               If no such chip is easily identifiable,
               the implementor should identify the chip
               which actually gathers the transmit
               and receive statistics and error
               indications. This would allow a
               manager station to correlate the
               statistics and the chip generating
               them, giving it the ability to take
               into account any known anomalies
               in the chip.
               
               This object has been deprecated.  Implementation
               feedback indicates that it is of limited use for
               debugging network problems in the field, and
               the administrative overhead involved in
               maintaining a registry of chipset OIDs is not
               justified.";
            smi:oid "1.3.6.1.2.1.10.7.2.1.17";
         }

         leaf dot3StatsSymbolErrors {
            type yang:counter32;
            config false;
            description   
              "For an interface operating at 100 Mb/s, the
               number of times there was an invalid data symbol
               when a valid carrier was present.
               
               For an interface operating in half-duplex mode
               at 1000 Mb/s, the number of times the receiving
               media is non-idle (a carrier event) for a period
               of time equal to or greater than slotTime, and
               during which there was at least one occurrence
               of an event that causes the PHY to indicate
               'Data reception error' or 'carrier extend error'
               on the GMII.
               
               For an interface operating in full-duplex mode
               at 1000 Mb/s, the number of times the receiving
               media is non-idle (a carrier event) for a period
               of time equal to or greater than minFrameSize,
               and during which there was at least one
               occurrence of an event that causes the PHY to
               indicate 'Data reception error' on the GMII.
               
               For an interface operating at 10 Gb/s, the
               number of times the receiving media is non-idle
               (a carrier event) for a period of time equal to
               or greater than minFrameSize, and during which
               there was at least one occurrence of an event
               that causes the PHY to indicate 'Receive Error'
               on the XGMII.
               
               The count represented by an instance of this
               object is incremented at most once per carrier
               event, even if multiple symbol errors occur
               during the carrier event.  This count does
               not increment if a collision is present.
               
               This counter does not increment when the
               interface is operating at 10 Mb/s.
               
               For interfaces operating at 10 Gb/s, this
               counter can roll over in less than 5 minutes if
               it is incrementing at its maximum rate.  Since
               that amount of time could be less than a
               
               management station's poll cycle time, in order
               to avoid a loss of information, a management
               station is advised to poll the
               dot3HCStatsSymbolErrors object for 10 Gb/s
               or faster interfaces.
               
               Discontinuities in the value of this counter can
               occur at re-initialization of the management
               system, and at other times as indicated by the
               value of ifCounterDiscontinuityTime.";
            reference 
              "[IEEE 802.3 Std.], 30.3.2.1.5,
               aSymbolErrorDuringCarrier.";
            smi:oid "1.3.6.1.2.1.10.7.2.1.18";
         }

         leaf dot3StatsDuplexStatus {
            type enumeration {
               enum unknown    { value 1; }
               enum halfDuplex { value 2; }
               enum fullDuplex { value 3; }
            }
            config false;
            description   
              "The current mode of operation of the MAC
               entity.  'unknown' indicates that the current
               duplex mode could not be determined.
               
               Management control of the duplex mode is
               accomplished through the MAU MIB.  When
               an interface does not support autonegotiation,
               or when autonegotiation is not enabled, the
               duplex mode is controlled using
               ifMauDefaultType.  When autonegotiation is
               supported and enabled, duplex mode is controlled
               using ifMauAutoNegAdvertisedBits.  In either
               case, the currently operating duplex mode is
               reflected both in this object and in ifMauType.
               
               Note that this object provides redundant
               information with ifMauType.  Normally, redundant
               objects are discouraged.  However, in this
               instance, it allows a management application to
               determine the duplex status of an interface
               without having to know every possible value of
               ifMauType.  This was felt to be sufficiently
               valuable to justify the redundancy.";
            reference 
              "[IEEE 802.3 Std.], 30.3.1.1.32,
               aDuplexStatus.";
            smi:oid "1.3.6.1.2.1.10.7.2.1.19";
         }

         leaf dot3StatsRateControlAbility {
            type smiv2:TruthValue;
            config false;
            description   
              "'true' for interfaces operating at speeds above
               1000 Mb/s that support Rate Control through
               lowering the average data rate of the MAC
               sublayer, with frame granularity, and 'false'
               otherwise.";
            reference 
              "[IEEE 802.3 Std.], 30.3.1.1.33,
               aRateControlAbility.";
            smi:oid "1.3.6.1.2.1.10.7.2.1.20";
         }

         leaf dot3StatsRateControlStatus {
            type enumeration {
               enum rateControlOff { value 1; }
               enum rateControlOn  { value 2; }
               enum unknown        { value 3; }
            }
            config false;
            description   
              "The current Rate Control mode of operation of
               the MAC sublayer of this interface.";
            reference 
              "[IEEE 802.3 Std.], 30.3.1.1.34,
               aRateControlStatus.";
            smi:oid "1.3.6.1.2.1.10.7.2.1.21";
         }
      }


      /* XXX table comments here XXX */

      list dot3CollEntry {

         key "ifIndex dot3CollCount";
         description 
           "A cell in the histogram of per-frame
            collisions for a particular interface.  An
            
            instance of this object represents the
            frequency of individual MAC frames for which
            the transmission (successful or otherwise) on a
            particular interface is accompanied by a
            particular number of media collisions.";
         smi:oid "1.3.6.1.2.1.10.7.5.1";

         leaf ifIndex {
            type leafref {
               path "/if-mib:interfaces/if-mib:ifEntry/if-mib:ifIndex";
            }
            // config false;
            description   
              "Automagically generated leafref leaf.";
         }

         leaf dot3CollCount {
            type int32 {
               range "1..16";
            }
            // config false;
            description   
              "The number of per-frame media collisions for
               which a particular collision histogram cell
               represents the frequency on a particular
               interface.";
            smi:oid "1.3.6.1.2.1.10.7.5.1.2";
         }

         leaf dot3CollFrequencies {
            type yang:counter32;
            config false;
            description   
              "A count of individual MAC frames for which the
               transmission (successful or otherwise) on a
               particular interface occurs after the
               frame has experienced exactly the number
               of collisions in the associated
               dot3CollCount object.
               
               For example, a frame which is transmitted
               on interface 77 after experiencing
               exactly 4 collisions would be indicated
               by incrementing only dot3CollFrequencies.77.4.
               No other instance of dot3CollFrequencies would
               be incremented in this example.
               
               This counter does not increment when the
               interface is operating in full-duplex mode.
               
               Discontinuities in the value of this counter can
               
               occur at re-initialization of the management
               system, and at other times as indicated by the
               value of ifCounterDiscontinuityTime.";
            smi:oid "1.3.6.1.2.1.10.7.5.1.3";
         }
      }




      /* XXX table comments here XXX */

      list dot3ControlEntry {

         key "dot3StatsIndex";
         description 
           "An entry in the table, containing information
            about the MAC Control sublayer on a single
            ethernet-like interface.";
         smi:oid "1.3.6.1.2.1.10.7.9.1";

         leaf dot3StatsIndex {
            type leafref {
               path "/etherlike-mib:dot3/etherlike-mib:dot3StatsEntry/etherlike-mib:dot3StatsIndex";
            }
            // config false;
            description   
              "Automagically generated leafref leaf.";
         }

         leaf dot3ControlFunctionsSupported {
            type bits {
               bit pause { position 0; }
            }
            config false;
            description   
              "A list of the possible MAC Control functions
               implemented for this interface.";
            reference 
              "[IEEE 802.3 Std.], 30.3.3.2,
               aMACControlFunctionsSupported.";
            smi:oid "1.3.6.1.2.1.10.7.9.1.1";
         }

         leaf dot3ControlInUnknownOpcodes {
            type yang:counter32;
            config false;
            description   
              "A count of MAC Control frames received on this
               interface that contain an opcode that is not
               supported by this device.
               
               For interfaces operating at 10 Gb/s, this
               counter can roll over in less than 5 minutes if
               it is incrementing at its maximum rate.  Since
               that amount of time could be less than a
               management station's poll cycle time, in order
               to avoid a loss of information, a management
               station is advised to poll the
               dot3HCControlInUnknownOpcodes object for 10 Gb/s
               or faster interfaces.
               
               Discontinuities in the value of this counter can
               occur at re-initialization of the management
               system, and at other times as indicated by the
               value of ifCounterDiscontinuityTime.";
            reference 
              "[IEEE 802.3 Std.], 30.3.3.5,
               aUnsupportedOpcodesReceived";
            smi:oid "1.3.6.1.2.1.10.7.9.1.2";
         }

         leaf dot3HCControlInUnknownOpcodes {
            type yang:counter64;
            config false;
            description   
              "A count of MAC Control frames received on this
               interface that contain an opcode that is not
               supported by this device.
               
               This counter is a 64 bit version of
               dot3ControlInUnknownOpcodes.  It should be used
               on interfaces operating at 10 Gb/s or faster.
               
               Discontinuities in the value of this counter can
               occur at re-initialization of the management
               system, and at other times as indicated by the
               value of ifCounterDiscontinuityTime.";
            reference 
              "[IEEE 802.3 Std.], 30.3.3.5,
               aUnsupportedOpcodesReceived";
            smi:oid "1.3.6.1.2.1.10.7.9.1.3";
         }
      }


      /* XXX table comments here XXX */

      list dot3PauseEntry {

         key "dot3StatsIndex";
         description 
           "An entry in the table, containing information
            about the MAC Control PAUSE function on a single
            ethernet-like interface.";
         smi:oid "1.3.6.1.2.1.10.7.10.1";

         leaf dot3StatsIndex {
            type leafref {
               path "/etherlike-mib:dot3/etherlike-mib:dot3StatsEntry/etherlike-mib:dot3StatsIndex";
            }
            // config false;
            description   
              "Automagically generated leafref leaf.";
         }

         leaf dot3PauseAdminMode {
            type enumeration {
               enum disabled          { value 1; }
               enum enabledXmit       { value 2; }
               enum enabledRcv        { value 3; }
               enum enabledXmitAndRcv { value 4; }
            }
            config true;
            description   
              "This object is used to configure the default
               administrative PAUSE mode for this interface.
               
               This object represents the
               administratively-configured PAUSE mode for this
               interface.  If auto-negotiation is not enabled
               or is not implemented for the active MAU
               attached to this interface, the value of this
               object determines the operational PAUSE mode
               of the interface whenever it is operating in
               full-duplex mode.  In this case, a set to this
               object will force the interface into the
               specified mode.
               
               If auto-negotiation is implemented and enabled
               for the MAU attached to this interface, the
               PAUSE mode for this interface is determined by
               auto-negotiation, and the value of this object
               denotes the mode to which the interface will
               automatically revert if/when auto-negotiation is
               later disabled.  Note that when auto-negotiation
               is running, administrative control of the PAUSE
               mode may be accomplished using the
               ifMauAutoNegCapAdvertisedBits object in the
               MAU-MIB.
               
               Note that the value of this object is ignored
               when the interface is not operating in
               full-duplex mode.
               
               An attempt to set this object to
               'enabledXmit(2)' or 'enabledRcv(3)' will fail
               on interfaces that do not support operation
               at greater than 100 Mb/s.";
            smi:oid "1.3.6.1.2.1.10.7.10.1.1";
         }

         leaf dot3PauseOperMode {
            type enumeration {
               enum disabled          { value 1; }
               enum enabledXmit       { value 2; }
               enum enabledRcv        { value 3; }
               enum enabledXmitAndRcv { value 4; }
            }
            config false;
            description   
              "This object reflects the PAUSE mode currently
               
               in use on this interface, as determined by
               either (1) the result of the auto-negotiation
               function or (2) if auto-negotiation is not
               enabled or is not implemented for the active MAU
               attached to this interface, by the value of
               dot3PauseAdminMode.  Interfaces operating at
               100 Mb/s or less will never return
               'enabledXmit(2)' or 'enabledRcv(3)'.  Interfaces
               operating in half-duplex mode will always return
               'disabled(1)'.  Interfaces on which
               auto-negotiation is enabled but not yet
               completed should return the value
               'disabled(1)'.";
            smi:oid "1.3.6.1.2.1.10.7.10.1.2";
         }

         leaf dot3InPauseFrames {
            type yang:counter32;
            config false;
            description   
              "A count of MAC Control frames received on this
               interface with an opcode indicating the PAUSE
               operation.
               
               This counter does not increment when the
               interface is operating in half-duplex mode.
               
               For interfaces operating at 10 Gb/s, this
               counter can roll over in less than 5 minutes if
               it is incrementing at its maximum rate.  Since
               that amount of time could be less than a
               management station's poll cycle time, in order
               to avoid a loss of information, a management
               station is advised to poll the
               dot3HCInPauseFrames object for 10 Gb/s or
               faster interfaces.
               
               Discontinuities in the value of this counter can
               occur at re-initialization of the management
               system, and at other times as indicated by the
               value of ifCounterDiscontinuityTime.";
            reference 
              "[IEEE 802.3 Std.], 30.3.4.3,
               aPAUSEMACCtrlFramesReceived.";
            smi:oid "1.3.6.1.2.1.10.7.10.1.3";
         }

         leaf dot3OutPauseFrames {
            type yang:counter32;
            config false;
            description   
              "A count of MAC Control frames transmitted on
               this interface with an opcode indicating the
               PAUSE operation.
               
               This counter does not increment when the
               interface is operating in half-duplex mode.
               
               For interfaces operating at 10 Gb/s, this
               counter can roll over in less than 5 minutes if
               it is incrementing at its maximum rate.  Since
               that amount of time could be less than a
               management station's poll cycle time, in order
               to avoid a loss of information, a management
               station is advised to poll the
               dot3HCOutPauseFrames object for 10 Gb/s or
               faster interfaces.
               
               Discontinuities in the value of this counter can
               occur at re-initialization of the management
               system, and at other times as indicated by the
               value of ifCounterDiscontinuityTime.";
            reference 
              "[IEEE 802.3 Std.], 30.3.4.2,
               aPAUSEMACCtrlFramesTransmitted.";
            smi:oid "1.3.6.1.2.1.10.7.10.1.4";
         }

         leaf dot3HCInPauseFrames {
            type yang:counter64;
            config false;
            description   
              "A count of MAC Control frames received on this
               interface with an opcode indicating the PAUSE
               operation.
               
               This counter does not increment when the
               interface is operating in half-duplex mode.
               
               This counter is a 64 bit version of
               dot3InPauseFrames.  It should be used on
               interfaces operating at 10 Gb/s or faster.
               
               Discontinuities in the value of this counter can
               occur at re-initialization of the management
               system, and at other times as indicated by the
               value of ifCounterDiscontinuityTime.";
            reference 
              "[IEEE 802.3 Std.], 30.3.4.3,
               aPAUSEMACCtrlFramesReceived.";
            smi:oid "1.3.6.1.2.1.10.7.10.1.5";
         }

         leaf dot3HCOutPauseFrames {
            type yang:counter64;
            config false;
            description   
              "A count of MAC Control frames transmitted on
               this interface with an opcode indicating the
               PAUSE operation.
               
               This counter does not increment when the
               interface is operating in half-duplex mode.
               
               This counter is a 64 bit version of
               dot3OutPauseFrames.  It should be used on
               interfaces operating at 10 Gb/s or faster.
               
               Discontinuities in the value of this counter can
               occur at re-initialization of the management
               system, and at other times as indicated by the
               value of ifCounterDiscontinuityTime.";
            reference 
              "[IEEE 802.3 Std.], 30.3.4.2,
               aPAUSEMACCtrlFramesTransmitted.";
            smi:oid "1.3.6.1.2.1.10.7.10.1.6";
         }
      }


      /* XXX table comments here XXX */

      list dot3HCStatsEntry {

         key "dot3StatsIndex";
         description 
           "An entry containing 64-bit statistics for a
            single ethernet-like interface.";
         smi:oid "1.3.6.1.2.1.10.7.11.1";

         leaf dot3StatsIndex {
            type leafref {
               path "/etherlike-mib:dot3/etherlike-mib:dot3StatsEntry/etherlike-mib:dot3StatsIndex";
            }
            // config false;
            description   
              "Automagically generated leafref leaf.";
         }

         leaf dot3HCStatsAlignmentErrors {
            type yang:counter64;
            config false;
            description   
              "A count of frames received on a particular
               interface that are not an integral number of
               octets in length and do not pass the FCS check.
               
               The count represented by an instance of this
               object is incremented when the alignmentError
               status is returned by the MAC service to the
               LLC (or other MAC user). Received frames for
               which multiple error conditions pertain are,
               according to the conventions of IEEE 802.3
               Layer Management, counted exclusively according
               to the error status presented to the LLC.
               
               This counter does not increment for group
               encoding schemes greater than 4 bits per group.
               
               This counter is a 64 bit version of
               dot3StatsAlignmentErrors.  It should be used
               on interfaces operating at 10 Gb/s or faster.
               
               Discontinuities in the value of this counter can
               occur at re-initialization of the management
               
               system, and at other times as indicated by the
               value of ifCounterDiscontinuityTime.";
            reference 
              "[IEEE 802.3 Std.], 30.3.1.1.7,
               aAlignmentErrors";
            smi:oid "1.3.6.1.2.1.10.7.11.1.1";
         }

         leaf dot3HCStatsFCSErrors {
            type yang:counter64;
            config false;
            description   
              "A count of frames received on a particular
               interface that are an integral number of octets
               in length but do not pass the FCS check.  This
               count does not include frames received with
               frame-too-long or frame-too-short error.
               
               The count represented by an instance of this
               object is incremented when the frameCheckError
               status is returned by the MAC service to the
               LLC (or other MAC user). Received frames for
               which multiple error conditions pertain are,
               according to the conventions of IEEE 802.3
               Layer Management, counted exclusively according
               to the error status presented to the LLC.
               
               Note:  Coding errors detected by the physical
               layer for speeds above 10 Mb/s will cause the
               frame to fail the FCS check.
               
               This counter is a 64 bit version of
               dot3StatsFCSErrors.  It should be used on
               interfaces operating at 10 Gb/s or faster.
               
               Discontinuities in the value of this counter can
               occur at re-initialization of the management
               system, and at other times as indicated by the
               value of ifCounterDiscontinuityTime.";
            reference 
              "[IEEE 802.3 Std.], 30.3.1.1.6,
               aFrameCheckSequenceErrors.";
            smi:oid "1.3.6.1.2.1.10.7.11.1.2";
         }

         leaf dot3HCStatsInternalMacTransmitErrors {
            type yang:counter64;
            config false;
            description   
              "A count of frames for which transmission on a
               particular interface fails due to an internal
               MAC sublayer transmit error. A frame is only
               
               counted by an instance of this object if it is
               not counted by the corresponding instance of
               either the dot3StatsLateCollisions object, the
               dot3StatsExcessiveCollisions object, or the
               dot3StatsCarrierSenseErrors object.
               
               The precise meaning of the count represented by
               an instance of this object is implementation-
               specific.  In particular, an instance of this
               object may represent a count of transmission
               errors on a particular interface that are not
               otherwise counted.
               
               This counter is a 64 bit version of
               dot3StatsInternalMacTransmitErrors.  It should
               be used on interfaces operating at 10 Gb/s or
               faster.
               
               Discontinuities in the value of this counter can
               occur at re-initialization of the management
               system, and at other times as indicated by the
               value of ifCounterDiscontinuityTime.";
            reference 
              "[IEEE 802.3 Std.], 30.3.1.1.12,
               aFramesLostDueToIntMACXmitError.";
            smi:oid "1.3.6.1.2.1.10.7.11.1.3";
         }

         leaf dot3HCStatsFrameTooLongs {
            type yang:counter64;
            config false;
            description   
              "A count of frames received on a particular
               interface that exceed the maximum permitted
               frame size.
               
               The count represented by an instance of this
               object is incremented when the frameTooLong
               status is returned by the MAC service to the
               LLC (or other MAC user). Received frames for
               which multiple error conditions pertain are,
               according to the conventions of IEEE 802.3
               Layer Management, counted exclusively according
               to the error status presented to the LLC.
               
               This counter is a 64 bit version of
               dot3StatsFrameTooLongs.  It should be used on
               interfaces operating at 10 Gb/s or faster.
               
               Discontinuities in the value of this counter can
               
               occur at re-initialization of the management
               system, and at other times as indicated by the
               value of ifCounterDiscontinuityTime.";
            reference 
              "[IEEE 802.3 Std.], 30.3.1.1.25,
               aFrameTooLongErrors.";
            smi:oid "1.3.6.1.2.1.10.7.11.1.4";
         }

         leaf dot3HCStatsInternalMacReceiveErrors {
            type yang:counter64;
            config false;
            description   
              "A count of frames for which reception on a
               particular interface fails due to an internal
               MAC sublayer receive error. A frame is only
               counted by an instance of this object if it is
               not counted by the corresponding instance of
               either the dot3StatsFrameTooLongs object, the
               dot3StatsAlignmentErrors object, or the
               dot3StatsFCSErrors object.
               
               The precise meaning of the count represented by
               an instance of this object is implementation-
               specific.  In particular, an instance of this
               object may represent a count of receive errors
               on a particular interface that are not
               otherwise counted.
               
               This counter is a 64 bit version of
               dot3StatsInternalMacReceiveErrors.  It should be
               used on interfaces operating at 10 Gb/s or
               faster.
               
               Discontinuities in the value of this counter can
               occur at re-initialization of the management
               system, and at other times as indicated by the
               value of ifCounterDiscontinuityTime.";
            reference 
              "[IEEE 802.3 Std.], 30.3.1.1.15,
               aFramesLostDueToIntMACRcvError.";
            smi:oid "1.3.6.1.2.1.10.7.11.1.5";
         }

         leaf dot3HCStatsSymbolErrors {
            type yang:counter64;
            config false;
            description   
              "For an interface operating at 100 Mb/s, the
               number of times there was an invalid data symbol
               when a valid carrier was present.
               
               For an interface operating in half-duplex mode
               at 1000 Mb/s, the number of times the receiving
               media is non-idle (a carrier event) for a period
               of time equal to or greater than slotTime, and
               during which there was at least one occurrence
               of an event that causes the PHY to indicate
               'Data reception error' or 'carrier extend error'
               on the GMII.
               
               For an interface operating in full-duplex mode
               at 1000 Mb/s, the number of times the receiving
               media is non-idle (a carrier event) for a period
               of time equal to or greater than minFrameSize,
               and during which there was at least one
               occurrence of an event that causes the PHY to
               indicate 'Data reception error' on the GMII.
               
               For an interface operating at 10 Gb/s, the
               number of times the receiving media is non-idle
               (a carrier event) for a period of time equal to
               or greater than minFrameSize, and during which
               there was at least one occurrence of an event
               that causes the PHY to indicate 'Receive Error'
               on the XGMII.
               
               The count represented by an instance of this
               object is incremented at most once per carrier
               event, even if multiple symbol errors occur
               during the carrier event.  This count does
               not increment if a collision is present.
               
               This counter is a 64 bit version of
               dot3StatsSymbolErrors.  It should be used on
               interfaces operating at 10 Gb/s or faster.
               
               Discontinuities in the value of this counter can
               occur at re-initialization of the management
               system, and at other times as indicated by the
               value of ifCounterDiscontinuityTime.";
            reference 
              "[IEEE 802.3 Std.], 30.3.2.1.5,
               aSymbolErrorDuringCarrier.";
            smi:oid "1.3.6.1.2.1.10.7.11.1.6";
         }
      }
      smi:oid "1.3.6.1.2.1.10.7";
   }

} /* end of module EtherLike-MIB */
