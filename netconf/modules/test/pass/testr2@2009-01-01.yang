module testr2 {

    namespace "http://netconfcentral.org/ns/testr2";
    prefix "r2";

    organization
        "Netconf Central";

    contact
        "Andy Bierman";

    description
        "YANG import-by-revision test module.";

    revision 2009-01-01 {
        description "Add C and D to the test grouping";
    }

    revision 2008-01-01 {
        description "Initial version.";
    }

    typedef TestType {
      type int32 {
        range 1..max;
      }
      default 5;
      units seconds;
    }

    grouping TestGroup {
       leaf A { type int64; }
       leaf B { type instance-identifier; } 
       leaf C { type string; }
       anyxml D;
       container E;
    }

    container bar-r2 {
       uses r2:TestGroup;
    }

}
