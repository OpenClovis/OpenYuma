module testgrouping3 {

    namespace "http://netconfcentral.org/ns/testgrouping3";

    prefix "foo3";

    import testgrouping2 { prefix foo2; }

    revision 2009-07-28 {
        description "Initial revision.";
    }

    augment /foo2:one/foo2:test-top {
       leaf my-leaf {
           type int32;
        }
     }
}
